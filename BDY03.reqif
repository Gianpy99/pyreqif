# BDY03

# Specification: BDY03

## STC-BDY02-446: Main beam telltale ON (ID:STC-HMI01-214)
Main beam ISO symbol shall be displayed to the driver when main beam latched function is active
- _Object type: Cross Functional Test
- _Status: REVIEWED
- _Procedure: 1.Set ignition state=5
  2.Set Master Light Switch Position = 2
  3.Active main beam latched function by pushing the DIMS stalk forwards to a latched position
- _Pass criteria: NFlashMainSwitch = (0x2),Main_Beam_Latched_ Available.
  Main beam ISO symbol shall be displayed on the driver display
- _Regression: Yes
- _Time [hr]: 0.2
- _Test environment: Lab-Car (manual)

## STC-BDY02-447: Main beam telltale OFF (ID:STC-HMI01-215)
Main beam ISO symbol shall be OFF on the driver when main beam latched function is NOT active
- _Object type: Cross Functional Test
- _Status: REVIEWED
- _Procedure: 1.Set ignition state<5
  2.Set Master Light Switch Position = 2
  3.Active main beam latched function by pushing the DIMS stalk forwards to a latched position
- _Pass criteria: NFlashMainSwitch = (0x0),Main_Beam_Latched_ Unavailable.
  Main beam ISO symbol shall be OFF on the driver display
- _Regression: Yes
- _Time [hr]: 0.2
- _Test environment: Lab-Car (manual)

## STC-BDY02-448: Main beam telltale OFF
Main beam ISO symbol shall be OFF on the driver when main beam latched function is NOT active
- _Object type: Negative Test
- _Status: REVIEWED
- _Procedure: 1.Set ignition state=5
  2.Set Master Light Switch Position = 0||1
  3.Active main beam latched function by pushing the DIMS stalk forwards to a latched position
- _Pass criteria: NFlashMainSwitch = (0x0),Main_Beam_Latched_ Unavailable.
  Main beam ISO symbol shall be OFF on the driver display
- _Regression: Yes
- _Time [hr]: 0.2
- _Test environment: Lab-Car (manual)

## STC-BDY02-449: Main beam telltale ON
Main beam ISO symbol shall be graphically displayed to the driver when main beam flash function is active
- _Object type: Nominal Test
- _Status: REVIEWED
- _Procedure: 1.Set ignition state >= 2
  2.Active main beam flash function by pulling the DIMS stalk towards the steering wheel to a momentary position
- _Pass criteria: NFlashMainSwitch = (0x1),Main_Beam_Flash_ Available.
  Main beam ISO symbol shall be displayed on the driver display
- _Regression: Yes
- _Time [hr]: 0.2
- _Test environment: Lab-Car (manual)

## STC-BDY02-450: Main beam telltale OFF
Main beam ISO symbol shall be graphically displayed to the driver when main beam flash function is NOT active
- _Object type: Negative Test
- _Status: REVIEWED
- _Procedure: 1.Set ignition state < 2
  2.Active main beam flash function by pulling the DIMS stalk towards the steering wheel to a momentary position
- _Pass criteria: 2.NFlashMainSwitch = (0x0),Main_Beam_Flash_ Inactive.
  Main beam ISO symbol shall be OFF on the driver display
- _Regression: Yes
- _Time [hr]: 0.2
- _Test environment: Lab-Car (manual)

## STC-BDY02-453: Main beam latched function available
Main beam latched function with master light position
- _Object type: Nominal Test
- _Status: REVIEWED
- _Procedure: 1.Set ignition state >= 5
  2.Set Master Light Switch Position = 2
- _Pass criteria: Main_Beam_Latched_ Available but not activated,
  NFlashMainSwitch = (0x0)
- _Regression: Yes
- _Time [hr]: 0.2
- _Test environment: Lab-Car (auto)

## STC-BDY02-455: Main beam latched function NOT available with igniton state
Main beam latched function NOT available when ignition state<5
- _Object type: Negative Test
- _Status: REVIEWED
- _Procedure: 1.Set ignition state <5
  2.Set Master Light Switch Position = 2
  3.Push the DIMS stalk forwards to a latched position
- _Pass criteria: Main beam latched function not available
- _Regression: Yes
- _Time [hr]: 0.2
- _Test environment: Lab-Car (auto)

## STC-BDY02-572: Main beam latched function NOT available with igniton state (ID:STC-ADA-02-08-530)
Main beam latched function NOT available when ignition state<5
- _Object type: Cross Functional Test
- _Status: REVIEWED
- _Procedure: 1.Set ignition state <5
  2.Set Master Light Switch Position = Auto
  3.Push the DIMS stalk forwards to a latched position
- _Pass criteria: Main beam latched function not available
- _Regression: Yes
- _Time [hr]: 0.2
- _Test environment: Lab-Car (auto)

## STC-BDY02-457: Main beam latched function deactivation with DIMS stalk
Deactivate main beam latched by pulling the DIMS stalk back from the latched position position
- _Object type: Nominal Test
- _Status: REVIEWED
- _Procedure:
  1. Set NIgnitionStatus >= 5
  2. Main Beam Latched Function Available && NFlashMainSwitch = (0x2)
  2.Pull the DIMS stalk back from the latched position
- _Pass criteria: 2.NFlashMainSwitch != (0x2),Main_Beam_Latched_ Inactive && NMainBeamStatus = Active
- _Regression: No
- _Time [hr]: 0.2
- _Test environment: Lab-Car (auto)

## STC-BDY02-458: Main beam latched function deactivation with ignition state
Deactivate main beam latched function with ignition state<5
- _Object type: Nominal Test
- _Status: REVIEWED
- _Procedure: 1.Activate main beam latched function i.e., NIgnitionStatus >= 5 && NFlashMainSwitch = (0x2)
  2.Set ignition state < 5
- _Pass criteria: 2.NMainBeamStatus = = Inactive
- _Regression: Yes
- _Time [hr]: 0.2
- _Test environment: Lab-Car (auto)

## STC-BDY02-1064: Main beam latched function deactivation with High severity
To cofirm ZB1 shall deactivate main beam latched when High severity crash occurs
- _Object type: Nominal Test
- _Status: REVIEWED
- _Procedure: 1.Activate main beam latched function i.e., NIgnitionStatus >= 5 && NFlashMainSwitch = (0x2)2.Simulate NCrashSeverity = High from ORC on Chassis CAN
- _Pass criteria: NMainBeamStatus = Inactive
- _Regression: No
- _Time [hr]: 0.2
- _Test environment: Lab-Car (auto)

## STC-BDY02-1065: Main beam latched function deactivation with low severity
To cofirm ZB1 shall deactivate main beam latched when Low severity crash occurs
- _Object type: Nominal Test
- _Status: REVIEWED
- _Procedure: 1.Activate main beam latched function i.e., NIgnitionStatus >= 5 && NFlashMainSwitch = (0x2)2.Simulate NCrashSeverity = Low from ORC on Chassis CAN
- _Pass criteria: NMainBeamStatus = Inactive
- _Regression: No
- _Time [hr]: 0.2
- _Test environment: Lab-Car (auto)

## STC-BDY02-459: Main beam latched function deactivation with master light
main beam latched function deactivation with master light switch position
- _Object type: Nominal Test
- _Status: REVIEWED
- _Procedure: 1.Activate main beam latched function i.e., NIgnitionStatus >= 5 && NFlashMainSwitch = (0x2)
  2.Set Master Light Switch Position = 0||1
- _Pass criteria: 2.NFlashMainSwitch = 0x0,Main_Beam_Latched_ Unavailable
- _Regression: No
- _Time [hr]: 0.2
- _Test environment: Lab-Car (auto)

## STC-BDY02-462: Main beam flash function activation
Main beam flash function activation with DIMS stalk
- _Object type: Nominal Test
- _Status: REVIEWED
- _Procedure: 1.Set ignition state = 2
  2.Pull the DIMS stalk towards the steering wheel to a momentary position
  3.Repeast step 2 for all ignition states 3,4,5 and 6
- _Pass criteria: Main_Beam_Flash_ Active.
  NFlashMainSwitch = (0x1)
- _Regression: No
- _Time [hr]: 0.2
- _Test environment: Lab-Car (auto)

## STC-BDY02-474: Main beam latched activation
Main beam fucntion activation
- _Object type: Nominal Test
- _Status: REVIEWED
- _Procedure: 1.Set ignition state>=5
  2.Enable main beam latched function by
  pushing the DIMS stalk forwards to a latched position
- _Pass criteria: Main beam latched activated
- _Regression: No
- _Time [hr]: 0.1
- _Test environment: Lab-Car (auto)

## STC-BDY02-574: Main beam flash function inactivation with release of DIMS stalk
Main beam flash function deactivation when ignition state<2
- _Object type: Nominal Test
- _Status: REVIEWED
- _Procedure: 1.Activate main beam flash function
  2.Release DIMS stalk while main flash function is in activation
- _Pass criteria: 2. NMainBeamStatus = Inactive
  NFlashMainSwitch != Flash
- _Regression: No
- _Time [hr]: 0.2
- _Test environment: Lab-Car (auto)

## STC-BDY02-1626: Main Beam Flash Function Deactivation
The main beam flash function shall be deactivated in the event of an ignition state transition to any state less than Ignition (5) or the state Connected Awake (7).
- _Object type: Nominal Test
- _Status: REVIEWED
- _Procedure:
  1. NIgnitionStatus = 5
  2. NMainBeamStatus = Active
  3. NIgnitionStatus < Ignition
  ||
  NIgnitionStatus == Connected Awake
- _Pass criteria: 3. NMainBeamStatus = Inactive

## STC-BDY02-1442: High Beam Short circuit fault
To confirm High Beam diagnostic strategy when short circuit fault occurs
- _Object type: Nominal Test
- _Status: REVIEWED
- _Procedure: 1.Creat High Beam circuit fault i.e., short circuit fault
  2.After fault, make sure the drive feedback curent is out of normal operation thresholds
- _Pass criteria: NHighBeamActiveStatus = Fault && NMainBeamClusterMessage = Fault display on ICU
- _Regression: No
- _Time [hr]: 0.1
- _Test environment: Lab-Car (manual)

## STC-BDY02-1446: High Beam Activation (ID:STC-ADA02-08-522)
To confirm High Beam activation
- _Object type: Cross Functional Test
- _Status: REVIEWED
- _Procedure: 1.Set Iginition State >=5
  2.Activate Main beam flash latched function or main beam flash function
- _Pass criteria: NHighBeamActiveStatus = Active
- _Regression: No
- _Time [hr]: 0.1
- _Test environment: Lab-Car (auto)

## STC-BDY02-1443: High Beam open circuit fault
To confirm High Beam diagnostic strategy when open circuit fault occurs
- _Object type: Nominal Test
- _Status: REVIEWED
- _Procedure: 1.Creat DTRL circuit fault i.e., open circuit fault
  2.After fault, make sure the drive feedback curent is out of normal operation thresholds
- _Pass criteria: NHighBeamActiveStatus = Fault && NMainBeamClusterMessage = Fault display on ICU
- _Regression: No
- _Time [hr]: 0.1
- _Test environment: Lab-Car (manual)

## STC-BDY02-1444: High Beam circuit circuit fault reset
To confirm High Beam lights fault reset with new ignition cycle
- _Object type: Nominal Test
- _Status: REVIEWED
- _Procedure: 1.Creat DTRL circuit fault i.e., Open circuit fault
  2.After fault, make sure the drive feedback curent is out of normal operation thresholds
  3.Start new ignition cycle
- _Pass criteria: NHighBeamActiveStatus = Inactive && NMainBeamClusterMessage = Fault display shall e cleared on ICU
- _Regression: No
- _Time [hr]: 0.1
- _Test environment: Lab-Car (manual)

## STC-BDY02-593: MasterLightSwitchResistorLadder1 voltage
To confirm MasterLightSwitchResistorLadder1 voltage to detect MLS position
- _Object type: Nominal Test
- _Status: REVIEWED
- _Procedure: 1.Change MasterLightSwitchResistorLadder1 voltage to STEP1 i.e., Nominal voltage(1.46),Min vol(1.43),Max(1.49)
  2.Change MasterLightSwitchResistorLadder1 voltage to STEP2 i.e., Nominal voltage(2.12),Min vol(2.08),Max(2.16)
  3.Change MasterLightSwitchResistorLadder1 voltage to STEP3 i.e., Nominal voltage(2.83),Min vol(2.78),Max(2.89)
  4.Change MasterLightSwitchResistorLadder1 voltage to STEP4 i.e., Nominal voltage(3.58),Min vol(3.51),Max(3.65)
  5.Change MasterLightSwitchResistorLadder1 voltage to previous state i.e.,Nominal voltage (4.26),Min vol(4.17),Max(4.35)
  6.Change MasterLightSwitchResistorLadder1 voltage to
  FAULT_MLS(Open circuit/Short to batt) i.e., Nominal voltage(5),Min vol(4.75),Max(5)
  7.Change MasterLightSwitchResistorLadder1 voltage to FAULT_MLS(Short to gnd) i.e., Nominal voltage(0),Min vol(0),Max(0.75)
  8.Change MasterLightSwitchResistorLadder1 voltage to FAULT_MLS(Out of range) i.e.,
  > 0.75 and < 1.43,
  > 1.49 and < 2.08,
  > 2.16 and < 2.78,
  > 2.89 and < 3.51,
  > 3.65 and < 4.17,
  > 4.35 and < 4.75
- _Pass criteria: 1.MLS position is set to Off_NMastrLghtSwtchPos
  2.MLS position is set to Auto_NMastrLghtSwtchPos
  3.MLS position is set to Side_Lamps_NMastrLghtSwtchPos
  4.MLS position is set to Dipped_Beam_NMastrLghtSwtchPos
  5.MLS position is set to Previous State
  6.MLS position is set to Auto_NMastrLghtSwtchPos
  7.MLS position is set to Auto_NMastrLghtSwtchPos
  8.MLS position is set to Auto_NMastrLghtSwtchPos
- _Regression: No
- _Time [hr]: 0.2
- _Test environment: Lab-Car (auto)

## STC-BDY02-594: MasterLightSwitchResistorLadder2 voltage
To confirm MasterLightSwitchResistorLadder2 voltage to detect MLS Fog request
- _Object type: Nominal Test
- _Status: REVIEWED
- _Procedure: 1.Change MasterLightSwitchResistorLadder2 voltage to STEP1 i.e., Nominal voltage(3.85),Min vol(3.77),Max(3.93)
  2.Change MasterLightSwitchResistorLadder2 voltage to STEP2 i.e., Nominal voltage(TBD),Min vol(TBD),Max(TBD)
  3.Change MasterLightSwitchResistorLadder2 voltage to STEP3 i.e., Nominal voltage(2.04),Min vol(2),Max(2.08)
  4.Change MasterLightSwitchResistorLadder2 voltage to
  FAULT_MLS(Open circuit/Short to batt) i.e., Nominal voltage(5),Min vol(4.75),Max(5)
  5.Change MasterLightSwitchResistorLadder2 voltage to FAULT_MLS(Short to gnd) i.e., Nominal voltage(0),Min vol(0),Max(0.75)
  6.Change MasterLightSwitchResistorLadder2 voltage to FAULT_MLS(Out of range) i.e.,
  > 0.75 and < 2.0
  > 2.08 and < 3.77
  > 3.93 and < 4.75
- _Pass criteria: 1.MLS fog reuest is set to OFF_BOffOnState(No press)
  2.MLS fog reuest is set to OFF_BOffOnState(Front fog)
  3.MLS fog reuest is set to ON_BOffOnState(Rear fog)
  4.MLS fog reuest is set to OFF_BOffOnState
  5.MLS fog reuest is set to OFF_BOffOnState
  6.MLS fog reuest is set to OFF_BOffOnState
- _Regression: No
- _Time [hr]: 0.25
- _Test environment: Lab-Car (auto)

## STC-BDY02-595: MLS fault display
To confirm the user display when MLS is faulty
- _Object type: Nominal Test
- _Status: REVIEWED
- _Procedure: 1.Set MLS to faulty state,
  Set MasterLightSwitchResistorLadder1 /MasterLightSwitchResistorLadder2 voltage to
  FAULT_MLS(Open circuit/Short to batt) i.e., Nominal voltage(5),Min vol(4.75),Max(5)
- _Pass criteria: ZB1 shall set 0x01 TBC DTC along with the fault display on DD
- _Regression: No
- _Time [hr]: 0.5
- _Test environment: Lab-Car (auto)

## STC-BDY02-1435: MasterLightSwitchResistorLadder1 voltage
To confirm MasterLightSwitchResistorLadder1 voltage to detect MLS position
- _Object type: Nominal Test
- _Status: REVIEWED
- _Procedure: 1.Change MasterLightSwitchResistorLadder1 voltage to STEP1 i.e., Nominal voltage(1.46),Min vol(1.43),Max(1.49)
  2.Change MasterLightSwitchResistorLadder1 voltage to STEP2 i.e., Nominal voltage(2.12),Min vol(2.08),Max(2.16)
  3.Change MasterLightSwitchResistorLadder1 voltage to STEP3 i.e., Nominal voltage(2.83),Min vol(2.78),Max(2.89)
  4.Change MasterLightSwitchResistorLadder1 voltage to STEP4 i.e., Nominal voltage(3.58),Min vol(3.51),Max(3.65)
  5.Change MasterLightSwitchResistorLadder1 voltage to previous state i.e.,Nominal voltage (4.26),Min vol(4.17),Max(4.35)
  6.Change MasterLightSwitchResistorLadder1 voltage to
  FAULT_MLS(Open circuit/Short to batt) i.e., Nominal voltage(5),Min vol(4.75),Max(5)
  7.Change MasterLightSwitchResistorLadder1 voltage to FAULT_MLS(Short to gnd) i.e., Nominal voltage(0),Min vol(0),Max(0.75)
  8.Change MasterLightSwitchResistorLadder1 voltage to FAULT_MLS(Out of range) i.e.,
  > 0.75 and < 1.43,
  > 1.49 and < 2.08,
  > 2.16 and < 2.78,
  > 2.89 and < 3.51,
  > 3.65 and < 4.17,
  > 4.35 and < 4.75
- _Pass criteria: 1.MLS position is set to Off_NMastrLghtSwtchPos
  2.MLS position is set to Auto_NMastrLghtSwtchPos
  3.MLS position is set to Side_Lamps_NMastrLghtSwtchPos
  4.MLS position is set to Dipped_Beam_NMastrLghtSwtchPos
  5.MLS position is set to Previous State
  6.MLS position is set to Auto_NMastrLghtSwtchPos
  7.MLS position is set to Auto_NMastrLghtSwtchPos
  8.MLS position is set to Auto_NMastrLghtSwtchPos
- _Regression: No
- _Time [hr]: 0.2
- _Test environment: Lab-Car (auto)

## STC-BDY02-1436: MasterLightSwitchResistorLadder2 voltage
To confirm MasterLightSwitchResistorLadder2 voltage to detect MLS Fog request
- _Object type: Nominal Test
- _Status: REVIEWED
- _Procedure: 1.Change MasterLightSwitchResistorLadder2 voltage to STEP1 i.e., Nominal voltage(3.85),Min vol(3.77),Max(3.93)
  2.Change MasterLightSwitchResistorLadder2 voltage to STEP2 i.e., Nominal voltage(TBD),Min vol(TBD),Max(TBD)
  3.Change MasterLightSwitchResistorLadder2 voltage to STEP3 i.e., Nominal voltage(2.04),Min vol(2),Max(2.08)
  4.Change MasterLightSwitchResistorLadder2 voltage to
  FAULT_MLS(Open circuit/Short to batt) i.e., Nominal voltage(5),Min vol(4.75),Max(5)
  5.Change MasterLightSwitchResistorLadder2 voltage to FAULT_MLS(Short to gnd) i.e., Nominal voltage(0),Min vol(0),Max(0.75)
  6.Change MasterLightSwitchResistorLadder2 voltage to FAULT_MLS(Out of range) i.e.,
  > 0.75 and < 2.0
  > 2.08 and < 3.77
  > 3.93 and < 4.75
- _Pass criteria: 1.MLS fog reuest is set to OFF_BOffOnState(No press)
  2.MLS fog reuest is set to OFF_BOffOnState(Front fog)
  3.MLS fog reuest is set to ON_BOffOnState(Rear fog)
  4.MLS fog reuest is set to OFF_BOffOnState
  5.MLS fog reuest is set to OFF_BOffOnState
  6.MLS fog reuest is set to OFF_BOffOnState
- _Regression: No
- _Time [hr]: 0.25
- _Test environment: Lab-Car (auto)

## STC-BDY02-1437: MLS fault display
To confirm the user display when MLS is faulty
- _Object type: Nominal Test
- _Status: REVIEWED
- _Procedure: 1.Set MLS to faulty state,
  Set MasterLightSwitchResistorLadder1 /MasterLightSwitchResistorLadder2 voltage to
  FAULT_MLS(Open circuit/Short to batt) i.e., Nominal voltage(5),Min vol(4.75),Max(5)
- _Pass criteria: ZB1 shall set 0x01 TBC DTC along with the fault display on DD
- _Regression: No
- _Time [hr]: 0.5
- _Test environment: Lab-Car (auto)

## STC-BDY02-1088: NMasterLightStatus = Dipped beam latched (ID:STC-BDY03-51, STC-HMI01-209)
To confirm master light status as Dipped beam latched when dipped beam is activated
- _Object type: Cross Functional Test
- _Status: REVIEWED
- _Procedure: 1.Set ignition state =5
  2.Activate dipped beam function(i.e.,Position master light switch in 0x2)
  3.Check for NMasterLightStatus Ethernet signal
- _Pass criteria: NMasterLightStatus = 0x2(Dipped_Beam_NMasterLightStatus)
- _Regression: No
- _Time [hr]: 0.3
- _Test environment: Lab-Car (auto)

## STC-BDY02-1087: NMasterLightStatus = Side Lights (ID:STC-HMI01-226)
To confirm master light status as side lights when side light function is activated
- _Object type: Cross Functional Test
- _Status: REVIEWED
- _Procedure: 1.Set ignition state =5
  2.Activate side lights function(i.e.,Position master light switch in 0x1)
  3.Check for NMasterLightStatus Ethernet signal
- _Pass criteria: NMasterLightStatus = 0x1(Side_Lamps_NMasterLightStatus)
- _Regression: No
- _Time [hr]: 0.3
- _Test environment: Lab-Car (auto)

## STC-BDY02-1247: NMasterLightStatus = OFF Lights (ID:STC-ADA02-08-527)
To confirm master light status as OFF light when side light and the Dipped beam are inactive
- _Object type: Cross Functional Test
- _Status: REVIEWED
- _Procedure: 1.Set ignition state =5
  2. Set NSideLightLeftStatus == inactive && NSideLightRightStatus == inactive && NDippedBeamLeftStatus == inactive && NDippedBeamRightStatus == inactive
  3.Check for NMasterLightStatus Ethernet signal
- _Pass criteria: NMasterLightStatus = 0x0 (Off_NMasterLightStatus)
- _Regression: No
- _Time [hr]: 0.3
- _Test environment: Lab-Car (auto)

## STC-BDY02-1096: Dipped beam latch function inactivation with ignition state
To confirm dipped beam latched function inactivation when ignition state <5
- _Object type: Nominal Test
- _Status: REVIEWED
- _Procedure: 1.Activate dipped beam latched function( i.e.,Set NIgnitionStatus == Ignition || Powertrain Activation && Position NMasterLightSwitchPosition = 0x2(Dipped Beam))
  2.Set NIgnitionStatus < 0x5
- _Pass criteria: Dipped Beam Latched Function inactivation.
  NDippedBeamLeftStatus,NDippedBeamRightStatus=Off &&
  NLHDippedBeamLampActiveSts,NRHDippedBeamLampActiveSts=inActive
- _Regression: No
- _Time [hr]: 0.3
- _Test environment: Lab-Car (auto)

## STC-BDY02-1097: Dipped beam latch inactivation with ignition state
To confirm dipped beam latched function inactivation when ignition state = 0x7
- _Object type: Nominal Test
- _Status: REVIEWED
- _Procedure: 1.Activate dipped beam latched function( i.e.,Set NIgnitionStatus == Ignition || Powertrain Activation && Position NMasterLightSwitchPosition = 0x2(Dipped Beam))
  2.Set NIgnitionStatus == Connected Awake 0x7
- _Pass criteria: Dipped Beam Latched Function inactivation.
  NDippedBeamLeftStatus,NDippedBeamRightStatus=Off &&
  NLHDippedBeamLampActiveSts,NRHDippedBeamLampActiveSts=inActive
- _Regression: No
- _Time [hr]: 0.3
- _Test environment: Lab-Car (auto)

## STC-BDY02-1098: Dipped beam latch activation with High severity
To confirm dipped beam latched function activation with high severity
- _Object type: Nominal Test
- _Status: REVIEWED
- _Procedure: 1.Set NIgnitionStatus == 0x2
  2.Set NCrashSeverity=High
- _Pass criteria: Dipped Beam Latched Function Available.
  NDippedBeamLeftStatus,NDippedBeamRightStatus=On_NIlluminationActvStat &&
  NLHDippedBeamLampActiveSts,NRHDippedBeamLampActiveSts=Active_NActivatnSts
- _Regression: No
- _Time [hr]: 0.3
- _Test environment: Lab-Car (auto)

## STC-BDY02-1445: Dipped beam deactivation
Dipped beam fucntion deactivation when MLS = Side light position
- _Object type: Nominal Test
- _Status: REVIEWED
- _Procedure: 1.Activate Dipped beam
  Set ignition state>=5 && Master light switch position is at Dipped,Master Light Switch Position = 2
  2.Deactivate Dipped beam
  Set ignition state>=5 && Master light switch position is at Dipped,Master Light Switch Position = 1
- _Pass criteria: NDippedBeamLeftStatus = Inactive
  NDippedBeamRightStatus = Inactive
- _Regression: No
- _Time [hr]: 0.1
- _Test environment: Lab-Car (auto)

## STC-BDY02-1099: Dipped beam latch activation with Low severity
To confirm dipped beam latched function activation with low severity
- _Object type: Nominal Test
- _Status: REVIEWED
- _Procedure: 1.Set NIgnitionStatus == 0x2
  2.Set NCrashSeverity=Low
- _Pass criteria: Dipped Beam Latched Function Available.
  NDippedBeamLeftStatus,NDippedBeamRightStatus=On_NIlluminationActvStat &&
  NLHDippedBeamLampActiveSts,NRHDippedBeamLampActiveSts=Active_NActivatnSts
- _Regression: No
- _Time [hr]: 0.3
- _Test environment: Lab-Car (auto)

## STC-BDY02-596: Dipped beam while crash
dipped beam illumination when crash occurs
- _Object type: Nominal Test
- _Status: REVIEWED
- _Procedure: 1.Set iNgnition state=5
  2.Simulate NCrashSeverity == High Severity from ORC on Chassis CAN
  3.Simulate NCrashSeverity !== High Severity from ORC on Chassis CAN
- _Pass criteria: 2.Dipped beam lamps shall be illuminated
  3.Dipped beam lamps illumination shall be deactivated
- _Regression: Yes
- _Time [hr]: 0.5
- _Test environment: Lab-Car (auto)

## STC-BDY02-1092: ISO symbol when dipped beam is activated
To confirm ISO symbol when dipped beam is activated
- _Object type: Nominal Test
- _Status: REVIEWED
- _Procedure: 1.Activate dipped beam latched function( i.e.,Set NIgnitionStatus == Ignition || Powertrain Activation && Position NMasterLightSwitchPosition = 0x2(Dipped Beam))
  2.Check ISO symbol
- _Pass criteria: Driver Display dipped beam tell tale illuminated in DDP
- _Regression: No
- _Time [hr]: 0.3
- _Test environment: Lab-Car (manual)

## STC-BDY02-1091: Dipped beam latch function activation
To confirm dipped beam latched function activation with MLS=0x2
- _Object type: Nominal Test
- _Status: REVIEWED
- _Procedure: 1.Set NIgnitionStatus == Ignition || Powertrain Activation
  2.Position NMasterLightSwitchPosition = 0x2(Dipped Beam)
- _Pass criteria: Dipped Beam Latched Function Available.
  NDippedBeamLeftStatus,NDippedBeamRightStatus=On_NIlluminationActvStat &&
  NLHDippedBeamLampActiveSts,NRHDippedBeamLampActiveSts=Active_NActivatnSts
- _Regression: No
- _Time [hr]: 0.3
- _Test environment: Lab-Car (auto)

## STC-BDY02-1105: Rear lights activation with PWM
To confirm rear lights activation when PWM duty cycle is 88%
- _Object type: Nominal Test
- _Status: REVIEWED
- _Procedure: 1.Set NIgnitionState = 0x5
  || PowerTrainStatus = Torque Available
  2.Set PWM duty cycle to 88% using XCp i.e., TailLampsPWM = 88%
- _Pass criteria: NTailLampLeftStatus == Active
  NTailLampRightStatus == Active
  &&
  NLHTailLampActiveSts==Active_NActivatnSts
  NRHTailLampActiveSts==
  Active_NActivatnSts
- _Regression: No
- _Time [hr]: 0.2
- _Test environment: Lab-Car (auto)

## STC-BDY02-1101: Rear lights activation
To confirm rear lights activation when igniton>=2
- _Object type: Nominal Test
- _Status: REVIEWED
- _Procedure: NIgnitionStatus >= Awake (0x2) &&
  NIgnitionStatus != Connected Awake (0x7)
  2.Set Master Light Switch is in the side or dipped lights position
- _Pass criteria: NTailLightLeftStatus = Active
  NTailLightRightStatus = Active
- _Regression: No
- _Time [hr]: 0.2
- _Test environment: Lab-Car (auto)

## STC-BDY02-1107: Rear lamp Short circuit fault
To confirm Rear lights diagnostic strategy when short circuit fault occurs
- _Object type: Nominal Test
- _Status: REVIEWED
- _Procedure: 1.Creat rear lights circuit fault i.e., short circuit fault
  2.After fault, make sure the drive feedback curent is out of normal operation thresholds
- _Pass criteria: 1.NLHRearTailLampActiveSts = TailLampFault
  NRHRearTailLampActiveSts = TailLampFault
  2.A DTC shall be raised
  3.NTailLampClusterMessage = Fault shall be sent to ICU
- _Regression: No
- _Time [hr]: 0.1
- _Test environment: Lab-Car (auto)

## STC-BDY02-1110: Rear lamp Open circuit fault
To confirm Rear lights diagnostic strategy when Open circuit fault occurs
- _Object type: Nominal Test
- _Status: REVIEWED
- _Procedure: 1.Creat rear lights circuit fault i.e., Open circuit fault
  2.After fault, make sure the drive feedback curent is out of normal operation thresholds
- _Pass criteria: 1.NLHRearTailLampActiveSts = TailLampFault
  NRHRearTailLampActiveSts = TailLampFault
  2.A DTC shall be raised
  3.NTailLampClusterMessage = Fault shall be sent to ICU
- _Regression: No
- _Time [hr]: 0.1
- _Test environment: Lab-Car (auto)

## STC-BDY02-1109: Rear lamp circuit circuit fault reset
To confirm Rear lights fault reset with new ignition cycle
- _Object type: Nominal Test
- _Status: REVIEWED
- _Procedure: 1.Creat rear lights circuit fault i.e., Open circuit fault
  2.After fault, make sure the drive feedback curent is out of normal operation thresholds
  3.Start new ignition cycle
- _Pass criteria: NLHRearTailLampActiveSts = TailLampInactive
  NRHRearTailLampActiveSts = RearLampInactive
- _Regression: No
- _Time [hr]: 0.1
- _Test environment: Lab-Car (auto)

## STC-BDY02-1112: Dipped beam activation with Automatic Light
To confirm dipped beam active with automatic light
- _Object type: Nominal Test
- _Status: REVIEWED
- _Procedure: 1.Set NPowertrainStatus == Available
  2.Set
  NMasterLightSwitchPosition == Auto
  3.RLS shall request the dipped beam to be active i.e., NLightSwitchRequest == ON (0x01)
- _Pass criteria: ZB1 shall enable dipped beam activation, BLH_DippedBeamActivate_Req = Active
  BRH_DippedBeamActivate_Req = Active
- _Regression: No
- _Time [hr]: 0.1
- _Test environment: Lab-Car (auto)

## STC-BDY02-1116: Dipped beam deactivation with Automatic Light when MLS is in Side Light or Dipped Beam
To confirm dipped beam deactive with automatic light when MLS is in Side Light or Dipped Beam
- _Object type: Nominal Test
- _Status: REVIEWED
- _Procedure: 1.Activate dipped beam function(Set NPowertrainStatus == Available &&
  NMasterLightSwitchPosition == Auto && NLightSwitchRequest == ON (0x01))
  2. Set MLS is in Side Light or Dipped Beam
- _Pass criteria: ZB1 shall deactivate the dipped beam function , BLH_DippedBeamActivate_Req = Inactive
  BRH_DippedBeamActivate_Req = Inactive
- _Regression: No
- _Time [hr]: 0.1
- _Test environment: Lab-Car (auto)

## STC-BDY02-1115: Dipped beam deactivation with Automatic Light when Powertrain status is unavailable
To confirm dipped beam deactive with automatic light when Powertrain status is unavailable
- _Object type: Nominal Test
- _Status: REVIEWED
- _Procedure: 1.Activate dipped beam function(Set NPowertrainStatus == Available &&
  NMasterLightSwitchPosition == Auto && NLightSwitchRequest == ON (0x01))
  2. Set Powertrain status is unavailable, NPowertrainStatus !== Available
- _Pass criteria: ZB1 shall deactivate the dipped beam function , BLH_DippedBeamActivate_Req = Inactive
  BRH_DippedBeamActivate_Req = Inactive
- _Regression: No
- _Time [hr]: 0.1
- _Test environment: Lab-Car (auto)

## STC-BDY02-1117: Dipped beam deactivation with Automatic Light when Fog light is Active
To confirm dipped beam deactive with automatic light when Fog light is Active
- _Object type: Nominal Test
- _Status: REVIEWED
- _Procedure: 1.Activate dipped beam function(Set NPowertrainStatus == Available &&
  NMasterLightSwitchPosition == Auto && NLightSwitchRequest == ON (0x01))
  2. Activaate Fog light , NFogLightRStatus == Active
- _Pass criteria: ZB1 shall deactivate the dipped beam function , BLH_DippedBeamActivate_Req = Inactive
  BRH_DippedBeamActivate_Req = Inactive
- _Regression: No
- _Time [hr]: 0.1
- _Test environment: Lab-Car (auto)

## STC-BDY02-1114: Dipped beam deactivation with Automatic Light
To confirm dipped beam deactive with automatic light
- _Object type: Nominal Test
- _Status: REVIEWED
- _Procedure: 1.Activate dipped beam function(Set NPowertrainStatus == Available &&
  NMasterLightSwitchPosition == Auto && NLightSwitchRequest == ON (0x01))
  2.Light Switch Request is OFF, NLightSwitchRequest == OFF (0x00)
- _Pass criteria: ZB1 shall deactivate the dipped beam function , BLH_DippedBeamActivate_Req = Inactive
  BRH_DippedBeamActivate_Req = Inactive
- _Regression: No
- _Time [hr]: 0.1
- _Test environment: Lab-Car (auto)

## STC-BDY02-1121: Dipped beam activation with Automatic Light recovers only in next ign cycle
To confirm dipped beam function shall only recover after an ignition cycle with all valid singals
- _Object type: Nominal Test
- _Status: REVIEWED
- _Procedure: 1.Activate dipped beam function(Set NPowertrainStatus == Available &&
  NMasterLightSwitchPosition == Auto && NLightSwitchRequest == ON (0x01))
  2.Light Switch Request is OFF, NLightSwitchRequest == OFF(0x0)
  3.Set NLightSwitchRequest == ON (0x01)
  4.Restart the new ignition cycle
- _Pass criteria: ZB1 shall deactivate the dipped beam function , BLH_DippedBeamActivate_Req = Inactive
  BRH_DippedBeamActivate_Req = Inactive in the current ignition cycle.
  Dipped beam function shall recover only in the new ignition cycle
- _Regression: No
- _Time [hr]: 0.1
- _Test environment: Lab-Car (auto)

## STC-BDY02-1447: RLS Diagnostics
To confirm automatic light functuion when RLS is unavailable
- _Object type: Nominal Test
- _Status: REVIEWED
- _Procedure: 1.Set ignition state >=5
  2.Master Light Switch Position set as AUTO && NPowertrainStatus == Torque Available && (NIgnitionStatus == 0x5 || 0x6) && NFogLightStatus == Inactive && NLightSwitchRequest == Fault (0x02)
- _Pass criteria: NDippedBeamLeftStatus = Active
  NDippedBeamRightStatus = Active
- _Regression: No
- _Time [hr]: 0.1
- _Test environment: Lab-Car (auto)

## STC-BDY02-581: Off light function activation
Off light function activation when IGN>=5
- _Object type: Nominal Test
- _Status: REVIEWED
- _Procedure: 1.Set ignition state =5
  2.Set Master light switch to OFF position from Auto for time period >=MLSOFFPeriod
  3.Set vehicle speed <=4kph
  4.Off light function activation period < LampsOFFTimer
- _Pass criteria: OFF Light Function available.Dipped beam shall be deactivated
- _Regression: Yes
- _Time [hr]: 0.3
- _Test environment: Lab-Car (auto)

## STC-BDY02-590: Off light function activation
Off light function activation when IGN>=5
- _Object type: Nominal Test
- _Status: REVIEWED
- _Procedure: 1.Set ignition state =6(torque available)
  2.Set Master light switch to OFF position from Auto for time period >=MLSOFFPeriod
  3.Set vehicle speed <=4kph
  4.Off light function activation period < LampsOFFTimer
  5.Activate DTRL/Hazard/Main beam/DIMS function while Off light is being actve
- _Pass criteria: OFF Light Function available.Dipped beam shall be deactivated.
  DTRL, Hazards, Main Beam Flash and DIMS functions shall be still available when the OFF Light function is being activated
- _Regression: Yes
- _Time [hr]: 0.3
- _Test environment: Lab-Car (auto)

## STC-BDY02-585: Off light function unavailable
Off light function unavailable when vehicle speed > 4kph
- _Object type: Nominal Test
- _Status: REVIEWED
- _Procedure: 1.Set ignition state >=5
  2.Set Master light switch to OFF position from Auto for time period >=MLSOFFPeriod
  3.Set vehicle speed > 4kph
  4.Off light function activation period < LampsOFFTimer
- _Pass criteria: OFF Light Function Unavailable
- _Regression: No
- _Time [hr]: 0.3
- _Test environment: Lab-Car (auto)

## STC-BDY02-586: Off light function unavailable
Off light function unavailable with master light switch position is set to AUTO
- _Object type: Nominal Test
- _Status: REVIEWED
- _Procedure: 1.Set ignition state >=5
  2.Set Master light switch to OFF for time period >=MLSOFFPeriod
  3.Set vehicle speed <= 4kph
  4.Set MSL=Auto before Off light function activation period < LampsOFFTimer
- _Pass criteria: OFF Light Function available for timeperiod LampsOFFTimer(30sec)
- _Regression: No
- _Time [hr]: 0.3
- _Test environment: Lab-Car (auto)

## STC-BDY02-588: Off light function unavailable
Off light function unavailable with master light switch position is set to side lights
- _Object type: Nominal Test
- _Status: REVIEWED
- _Procedure: 1.Set ignition state >=5
  2.Set Master light switch to OFF for time period >=MLSOFFPeriod
  3.Set vehicle speed <= 4kph
  4.Set MSL=side lights before Off light function activation period < LampsOFFTimer
- _Pass criteria: OFF Light Function Unavailable
- _Regression: No
- _Time [hr]: 0.3
- _Test environment: Lab-Car (auto)

## STC-BDY02-589: Off light function unavailable
Off light function unavailable with master light switch position is set to dipped beam
- _Object type: Nominal Test
- _Status: REVIEWED
- _Procedure: 1.Set ignition state >=5
  2.Set Master light switch to OFF for time period >=MLSOFFPeriod
  3.Set vehicle speed <= 4kph
  4.Set MSL=dipped before Off light function activation period < LampsOFFTimer
- _Pass criteria: OFF Light Function Unavailable
- _Regression: No
- _Time [hr]: 0.3
- _Test environment: Lab-Car (auto)

## STC-BDY02-587: Off light function deactivation
Off light function deactivation after LampsOFFTimer duration
- _Object type: Nominal Test
- _Status: REVIEWED
- _Procedure: 1.Set ignition state >=5
  2.Set Master light switch to OFF position from Auto for time period >=MLSOFFPeriod
  3.Set vehicle speed <= 4kph
  4.Off light function activation period > LampsOFFTimer
- _Pass criteria: OFF Light Function deactivated for after 30sec
- _Regression: No
- _Time [hr]: 0.3
- _Test environment: Lab-Car (auto)

## STC-BDY02-1255: Dipped beam lamps status failure
To confirm ZB1 shall raise DTC when dipped beam lamp status failure
- _Object type: Nominal Test
- _Status: REVIEWED
- _Procedure: 1.Set NIgnitionStatus >= 0x05
  2.ZA1 receiver dipped beam lamps status failure signal from HeadLamp LIN, HeadLampsLIN::BStat_L_Failed == Failed ||
  HeadLampsLIN::BStat_R_Failed == Failed
- _Pass criteria: ZA1 shall Raise DTC,
  NLHDippedBeamLampActiveSts = Fault ||
  NRHDippedBeamLampActiveSts = Fault
- _Regression: No
- _Time [hr]: 0.1
- _Test environment: Lab-Car (auto)

## STC-BDY02-1448: Dipped beam lamps status failure error recovery
To confirm DTC Shall clear when dipped beam lamp status failure error has cleared
- _Object type: Nominal Test
- _Status: REVIEWED
- _Procedure: 1.Set NIgnitionStatus >= 0x05
  2.Activate Dipped beam lamp status error:
  HeadLampsLIN::BStat_L_Failed == Failed ||
  HeadLampsLIN::BStat_R_Failed == Failed
  3.Recover dipped beam status error:
  Send valid LIN message for 10 consecutive frames,
  HeadLampsLIN::BStat_L_Failed == OK ||
  HeadLampsLIN::BStat_R_Failed == OK
- _Pass criteria: ZA1 shall clear DTC,
  NLHDippedBeamLampActiveSts = OK ||
  NRHDippedBeamLampActiveSts = OK
- _Regression: No
- _Time [hr]: 0.1
- _Test environment: Lab-Car (auto)

## STC-BDY02-1449: Dipped Beam lamp Communications Failure
To confirm ZB1 Shall raise DTC when Dipped beam lamps communication failed
- _Object type: Nominal Test
- _Status: REVIEWED
- _Procedure: 1.Set NIgnitionStatus >= 0x05
  2.ZA1 receive Dipped beam lamps communication failure on HeadLamp LIN,
  HeadLampsLIN::BCOM_L_Failed == Failed ||
  HeadLampsLIN::BCOM_R_Failed == Failed
- _Pass criteria: ZA1 Shall Raise DTC
  NLHDippedBeamLampActiveSts = Fault ||
  NRHDippedBeamLampActiveSts = Fault
- _Regression: No
- _Time [hr]: 0.1
- _Test environment: Lab-Car (auto)

## STC-BDY02-1450: Dipped Beam lamp Communications Failure error recovery
To confirm DTC Shall clear when Dipped beam lamps communication failed error has cleared
- _Object type: Nominal Test
- _Status: REVIEWED
- _Procedure: 1.Set NIgnitionStatus >= 0x05
  2.Activate Dipped beam Communications Failure:
  HeadLampsLIN::BCOM_L_Failed == Failed ||
  HeadLampsLIN::BCOM_R_Failed == Failed
  3.Recover dipped beam Communications Failure:
  Send valid LIN message for 10 consecutive frames,
  HeadLampsLIN::BCOM_L_Failed == OK ||
  HeadLampsLIN::BCOM_R_Failed == OK
- _Pass criteria: NLHDippedBeamLampActiveSts = OK ||
  NRHDippedBeamLampActiveSts = OK
- _Regression: No
- _Time [hr]: 0.1
- _Test environment: Lab-Car (auto)

## STC-BDY02-1451: Dipped beam Thermal failure or FAN in the Lamp failure
To confirm ZB1 shall set DTC when Dipped beam Thermal failure or FAN in the Lamp failure
- _Object type: Nominal Test
- _Status: REVIEWED
- _Procedure: 1.Set NIgnitionStatus >= 0x05
  2.ZB1 receive Dipped beam Thermal failure or FAN in the Lamp failure on HeadLamp LIN,
  HeadLampsLIN::BFAN_L_Failed == Failed ||
  HeadLampsLIN::BFAN_R_Failed == Failed
- _Pass criteria: ZA1 shall Raise DTC
  NLHDippedBeamLampActiveSts = Fault ||
  NRHDippedBeamLampActiveSts = Fault
- _Regression: No
- _Time [hr]: 0.1
- _Test environment: Lab-Car (auto)

## STC-BDY02-1452: Dipped beam Thermal failure or FAN in the Lamp failure error recovery
To confirm DTC Shall clear Dipped beam Thermal failure or FAN in the Lamp failure error has cleared
- _Object type: Nominal Test
- _Status: REVIEWED
- _Procedure: 1.Set NIgnitionStatus >= 0x05
  2.Activate Dipped beam Thermal failure or FAN in the Lamp failure:
  HeadLampsLIN::BFAN_L_Failed == Failed ||
  HeadLampsLIN::BFAN_R_Failed == Failed
  3.Recover Dipped beam Thermal failure or FAN in the Lamp failure:
  Send valid LIN message for 10 consecutive frames,
  HeadLampsLIN::BFAN_L_Failed == OK ||
  HeadLampsLIN::BFAN_R_Failed == OK
- _Pass criteria: NLHDippedBeamLampActiveSts = OK ||
  NRHDippedBeamLampActiveSts = OK
- _Regression: No
- _Time [hr]: 0.1
- _Test environment: Lab-Car (auto)

## STC-BDY02-1453: Dipped Beam lamp Response Error
To confirm ZB1 shall raise DTC when Dipped Beam lamp Response Error
- _Object type: Nominal Test
- _Status: REVIEWED
- _Procedure: 1.Set NIgnitionStatus >= 0x05
  2.ZB1 receive Dipped Beam lamp Response Error
  on HeadLamp LIN,
  HeadLampsLIN::BBLRResponseError == Error ||
  HeadLampsLIN::BBLLResponseError== Error
- _Pass criteria: ZA1 shall Raise DTC
  NLHDippedBeamLampActiveSts = Fault ||
  NRHDippedBeamLampActiveSts = Fault
- _Regression: No
- _Time [hr]: 0.1
- _Test environment: Lab-Car (auto)

## STC-BDY02-1454: Dipped Beam lamp Response Error recovery
To confirm ZB1 shall clear DTC Dipped Beam lamp Response Error has cleared
- _Object type: Nominal Test
- _Status: REVIEWED
- _Procedure: 1.Set NIgnitionStatus >= 0x05
  2.Activate Dipped Beam lamp Response Error:
  HeadLampsLIN::BBLRResponseError == Error ||
  HeadLampsLIN::BBLLResponseError== Error
  3.Recover Dipped Beam lamp Response Error:
  Send valid LIN message for 10 consecutive frames,
  HeadLampsLIN::BBLRResponseError == No Error ||
  HeadLampsLIN::BBLLResponseError== No Error
- _Pass criteria: NLHDippedBeamLampActiveSts = OK ||
  NRHDippedBeamLampActiveSts = OK
- _Regression: No
- _Time [hr]: 0.1
- _Test environment: Lab-Car (auto)

## STC-BDY02-1455: Dipped Beam Power Supply of the lamp is Too Low
To confirm ZB1 shall raise DTC Dipped Beam Power Supply of the lamp is Too Low
- _Object type: Nominal Test
- _Status: REVIEWED
- _Procedure: 1.Set NIgnitionStatus >= 0x05
  2.ZB1 receive Dipped Beam Power Supply of the lamp is Too Low on HeadLamp LIN,
  HeadLampsLIN::BPowerSupply_L == Too Low ||
  HeadLampsLIN::BPowerSupply_R== Too Low
- _Pass criteria: ZA1 shall Raise DTC
  NLHDippedBeamLampActiveSts = Fault ||
  NRHDippedBeamLampActiveSts = Fault
- _Regression: No
- _Time [hr]: 0.1
- _Test environment: Lab-Car (auto)

## STC-BDY02-1456: Dipped Beam Power Supply of the lamp is Too Low Error recovery
To confirm ZB1 shall clear DTCDipped Beam Power Supply of the lamp is Too Low Error recovery
- _Object type: Nominal Test
- _Status: REVIEWED
- _Procedure: 1.Set NIgnitionStatus >= 0x05
  2.Dipped Beam Power Supply of the lamp is Too Low Error:
  HeadLampsLIN::BPowerSupply_L == Too Low ||
  HeadLampsLIN::BPowerSupply_R== Too Low
  3.Recover Dipped Beam Power Supply of the lamp is Too Low Error:
  Send valid LIN message for 10 consecutive frames,
  HeadLampsLIN::BPowerSupply_L == OK ||
  HeadLampsLIN::BPowerSupply_R== Ok
- _Pass criteria: NLHDippedBeamLampActiveSts = OK ||
  NRHDippedBeamLampActiveSts = OK
- _Regression: No
- _Time [hr]: 0.1
- _Test environment: Lab-Car (auto)

## STC-BDY02-1457: Dipped Beam open/short circuit failure
To confirm ZB1 shall raise DTC when Dipped Beam open/short circuit failure
- _Object type: Nominal Test
- _Status: REVIEWED
- _Procedure: 1.Set NIgnitionStatus >= 0x05
  2.Create Open/Short ciruit failure of the Dipped beam lamps
- _Pass criteria: ZB1 shall Raise DTC
  NLHDippedBeamLampActiveSts = Fault
  NRHDippedBeamLampActiveSts = Fault && NDippedBeamClusterMessage = Fault display on ICU
- _Regression: No
- _Time [hr]: 0.1
- _Test environment: Lab-Car (auto)

## STC-BDY02-1458: Dipped Beam open/short circuit failure recovery
To confirm ZB1 shall clear DTC when Dipped Beam open/short circuit failure Error recovery
- _Object type: Nominal Test
- _Status: REVIEWED
- _Procedure: 1.Set NIgnitionStatus >= 0x05
  2.Create Open/Short ciruit failure of the Dipped beam lamps, Drive feedback current out of normal operation range for debounce time
  3.Clear the fault:
  Drive feedback current within normal operation range for debounce time ||
  A new ignition cycle
- _Pass criteria: NLHDippedBeamLampActiveSts = Inactive
  NRHDippedBeamLampActiveSts = Inactive && NDippedBeamClusterMessage = Fault display shall be cleared on ICU
- _Regression: No
- _Time [hr]: 0.1
- _Test environment: Lab-Car (auto)

## STC-BDY02-1123: Side light function activation
To confirm side light function activation in ignition state =0x05
- _Object type: Nominal Test
- _Status: REVIEWED
- _Procedure: 1.Set NIgnitionStatus = 0x05
  2.NMasterLightSwitchPosition == Side Light || Dipped Beam
- _Pass criteria: NSideLightLeftStatus = Active NSideLightRightStatus = Active
- _Regression: No
- _Time [hr]: 0.1
- _Test environment: Lab-Car (auto)

## STC-BDY02-1124: Side light function activation with AUTO function
To confirm side light function activation with AUTO light activation
- _Object type: Nominal Test
- _Status: REVIEWED
- _Procedure: 1.Set NIgnitionStatus = 0x05 ||
  PowertrainStatus = Torque Available
  2.NMasterLightSwitchPosition == AUTO
- _Pass criteria: NSideLightLeftStatus = Active NSideLightRightStatus = Active
- _Regression: No
- _Time [hr]: 0.1
- _Test environment: Lab-Car (auto)

## STC-BDY02-1125: Side light function activation with dipped beam activation
To confirm side light function activation with dipped beam activation
- _Object type: Nominal Test
- _Status: REVIEWED
- _Procedure: NMasterLightSwitchPosition == OFF || AUTO
  && (NDippedBeamLeftStatus = Active NDippedBeamRightStatus = Active)
- _Pass criteria: NSideLightLeftStatus = Active NSideLightRightStatus = Active
- _Regression: No
- _Time [hr]: 0.1
- _Test environment: Lab-Car (auto)

## STC-BDY02-1126: Side light function deactivation with ignition state
To confirm side light function deactivation when ignition state !=0x05 || Powertrain Activation
- _Object type: Nominal Test
- _Status: REVIEWED
- _Procedure: 1.Set NIgnitionStatus = 0x05
  2.NMasterLightSwitchPosition == Side Light || Dipped Beam
  3.Set NIgnitionStatus !=0x05 || Powertrain Activation
- _Pass criteria: NSideLightLeftStatus = InActive NSideLightRightStatus = InActive
- _Regression: No
- _Time [hr]: 0.1
- _Test environment: Lab-Car (auto)

## STC-BDY02-1127: side & tail lamps illumination when side lights are activated
To confirm side & tail lamps illumination when side lights are activated
- _Object type: Nominal Test
- _Status: REVIEWED
- _Procedure: Activate side light function(Set NIgnitionStatus = 0x05
  && NMasterLightSwitchPosition == Side Light || Dipped Beam)
- _Pass criteria: BLH_SidelampPositionIndicator = Active
  BRH_SidelampPositionIndicator = Active
  NTailLightLeftStatus = Active
  NTailLightRightStatus = Active
- _Regression: No
- _Time [hr]: 0.1
- _Test environment: Lab-Car (auto)

## STC-BDY02-1128: ISO symbol when side lights function is activated
To confirm ISO symbol when side lights function is activated
- _Object type: Nominal Test
- _Status: REVIEWED
- _Procedure: 1.Activate side light function(Set NIgnitionStatus = 0x05
  && NMasterLightSwitchPosition == Side Light || Dipped Beam)
  2.Check ISO symbol
- _Pass criteria: Driver Display side lights tell tale illuminated in DDP
- _Regression: No
- _Time [hr]: 0.3
- _Test environment: Lab-Car (manual)

## STC-BDY02-228: Side Light control logic- Hazard ON
Side light function shall be deactivated when hazard is active
- _Object type: Nominal Test
- _Status: REVIEWED
- _Procedure: 1.NHazardStatus = 0x0 && NIndicatorLStatus =0x0 && NIndicatorRStatus = 0x0
  2.Set ignition status ≥ 5 && Master Light Switch Position = 1 || 2
  3.Set NHazardStatus= 0x1
  4.Set NHazardStatus= 0x0
- _Pass criteria: 2.Side lights active.
  NSideLightLeftStatus = (0x1) && NSideLightRightStatus = (0x1),
  NTailLightLeftStatus = (0x1) && NTailLightRightStatus = (0x1),
  NMasterLightStatus = (0x1)
  3.Side lights inactive.
  NSideLightLeftStatus = (0x0) && NSideLightRightStatus = (0x0),
  NMasterLightStatus = (0x1)
  NTailLightLeftStatus = (0x1) && NTailLightRightStatus = (0x1)
  4.Side lights active.
  NSideLightLeftStatus = (0x1) && NSideLightRightStatus = (0x1)
- _Regression: Yes
- _Time [hr]: 0.4
- _Test environment: Lab-Car (auto)

## STC-BDY02-1131: Side light Short circuit fault
To confirm Rear lights diagnostic strategy when short circuit fault occurs
- _Object type: Nominal Test
- _Status: REVIEWED
- _Procedure: 1.Creat Side light circuit fault i.e., short circuit fault
  2.After fault, make sure the drive feedback curent is out of normal operation thresholds
- _Pass criteria: NLHFrontLampActiveSts = SideLampInactive
  NRHFrontLampActiveSts = SideLampInactive
  2.A DTC shall be raised
  3.NSideLightClusterMessage = Fault
- _Regression: No
- _Time [hr]: 0.1
- _Test environment: Lab-Car (auto)

## STC-BDY02-1132: Side light open circuit fault
To confirm Rear lights diagnostic strategy when open circuit fault occurs
- _Object type: Nominal Test
- _Status: REVIEWED
- _Procedure: 1.Creat Side light circuit fault i.e., open circuit fault
  2.After fault, make sure the drive feedback curent is out of normal operation thresholds
- _Pass criteria: NLHFrontLampActiveSts = SideLampInactive
  NRHFrontLampActiveSts = SideLampInactive
  2.A DTC shall be raised
  3.NSideLightClusterMessage = Fault
- _Regression: No
- _Time [hr]: 0.1
- _Test environment: Lab-Car (auto)

## STC-BDY02-1133: Side light circuit circuit fault reset
To confirm Rear lights fault reset with new ignition cycle
- _Object type: Nominal Test
- _Status: REVIEWED
- _Procedure: 1.Creat Side light circuit fault i.e., Open circuit fault
  2.After fault, make sure the drive feedback curent is out of normal operation thresholds
  3.Start new ignition cycle
- _Pass criteria: NLHFrontLampActiveSts = SideLampInactive
  NRHFrontLampActiveSts = SideLampInactive
- _Regression: No
- _Time [hr]: 0.1
- _Test environment: Lab-Car (auto)

## STC-BDY02-1628: Approach Light Function Activation
The Approach Event shall be activated when the vehicle gets unlocked and the entry lighting is enabled and the battery state of charge is not low.
- _Object type: Nominal Test
- _Status: REVIEWED
- _Procedure: Preconditions:
  NTEntryLighting != OFF &&
  NBatteryLowStateOfCharge == OK
  1. Vehicle Unlocked
  NVehicleLockStatus [PE Lock] or [RKE Lock] -
  2. Vehicle locked
  NVehicleLockStatus [PE Unlock] or [RKE Unlock]
- _Pass criteria: 2. BApproachLightStatus = ON(0x1)
  NDippedBeamLeftStatus = ON
  NDippedBeamRightStatus = ON
  NSideLightLeftStatus = ON
  NSideLightRightStatus = ON
  NTailLightLeftStatus = ON
  NTailLightRightStatus = ON
- _Regression: No
- _Time [hr]: 0.2
- _Test environment: Lab-Car (manual)

## STC-BDY02-1629: TApproachLightTimer
The approach lighting function shall de-activated when RKE or PE Lock is detected or calibratable timer (TApproachLightTimer) expires.
- _Object type: Nominal Test
- _Status: REVIEWED
- _Procedure: BApproachLightStatus = ON &&
  NVehicleLockStatus == [PE Lock] or [RKE Lock]
  or
  Approach Light Function being activated for over than TApproachLightTimer
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1630: Approach Light Function Deactivation (ignition status)
The Approach Event shall be deactivated when Ignition State is greater than Ignition (0x5).
- _Object type: Nominal Test
- _Status: REVIEWED
- _Procedure: BApproachLightStatus = ON &&
  NIgnitionStatus > 0x5
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1631: Approach Light Function Deactivation (battery status)
The Approach Event shall be deactivated when the battery state of charge is low.
- _Object type: Nominal Test
- _Status: REVIEWED
- _Procedure: Preconditions:
  BApproachLightStatus = ON &&
  NBatteryLowStateOfCharge != OK
  Test:
  1. Lock the vehicle
- _Pass criteria: Verify that:
  BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1632: Approach Light Function Deactivation (entry light disabled)
The Approach Event shall be deactivated when the entry lighting is disabled on central display.
- _Object type: Nominal Test
- _Status: REVIEWED
- _Procedure: Preconditions:
  BApproachLightStatus = ON &&
  NTEntryLighting == OFF
  Test:
  1. Lock the vehicle
- _Pass criteria: Verify that:
  BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1633: Approach Light Function Deactivation (entry lighting timer)
The Approach Event shall be deactivated when the entry lighting timer is reached.
- _Object type: Nominal Test
- _Status: REVIEWED
- _Procedure: BApproachLightStatus = ON &&
  NTEntryLighting timer reached
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1634: Approach Light Function Deactivation (ADI comm fault)
The Approach Event shall be deactivated when ADI communication is in fault
- _Object type: Nominal Test
- _Status: REVIEWED
- _Procedure: BApproachLightStatus = ON &&
  ADI communication fault raised
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1461: Approach Light timer user config (ID: STC-CFG02-01-1150)
To confirm Approach Light timer user config
- _Object type: Cross Functional Test
- _Status: REVIEWED
- _Procedure: 1.Activate approach light function:
  NIgnitionStatus <= Awake &&
  NVehicleLockStatus == RKE Unlock
  2.Set TApproachLightTimer to different values using UserConfig settings from ADI:
  Reference SDS-CFG02-01-308
- _Pass criteria: TApproachLightTimer: set to >10secs
  0x0 = OFF
  0x1 = 10 Seconds
  0x2 = 15 Seconds
  0x3 = 20 Seconds
  0x4 = 30 Seconds
  0x5 = 40 Seconds
  0x6 = 50 Seconds
  0x7 = 60 Seconds
- _Regression: No
- _Time [hr]: 0.2
- _Test environment: Lab-Car (auto)

## STC-BDY02-375: Approach light user settings (ID:STC-CFG02-01-1150, STC-CFG02-01-1151, STC-CFG02-01-1152)
Approach light user settings using menu stalk and lighting timer
- _Object type: Cross Functional Test
- _Status: REVIEWED
- _Procedure: Set approach lighting timer as per below:
  NTEntryLighting Timer (
  )_x000D_
  f (0
  1 15
  30_x000D_3 45_x000D_4
  NMenuLStalkBackStatus, _x000D_NMenuLStalkForwardStatus
  NMenuLStalkDownStatus,_x000D_NMenuLStalkUpStatus
- _Pass criteria: NDippedBeamLeftStatus && NDippedBeamRightStatus shall follow the approach light timer and shall deactivate when timer expires
- _Regression: Yes
- _Time [hr]: 0.5
- _Test environment: Lab-Car (manual)

## STC-BDY02-1635: Approach Event lighting function timer configuration
The Approach Event lighting function timer shall be able to be configured by the user via Menu Stalk or contact screen
- _Object type: Nominal Test
- _Status: REVIEWED
- _Procedure: Check the central display and chenge the entry light time configuraion
- _Pass criteria: NTEntryLighting value changes according to the central display settings
- _Regression: No
- _Time [hr]: 0.1
- _Test environment: Lab-Car (manual)

## STC-BDY02-475: See You Home activation
- _Object type: Nominal Test
- _Status: REVIEWED
- _Procedure:
  1. Set Ignition State = 2
  2. Lock the car using RKE keys
- _Pass criteria:
  1. BSeeYouHomeStatus = ON
  & Dipped Beam ON,
  NDippedBeamLeftStatus = (0x1) && NDippedBeamRightStatus = (0x1)
- _Regression: Yes
- _Time [hr]: 0.5
- _Test environment: Lab-Car (auto)

## STC-BDY02-539: See You Home Activation
See You Home Activation when Left door transition to Open and timer > 0
- _Object type: Nominal Test
- _Status: REVIEWED
- _Procedure: 1.Set NIgnitionStatus=2
  2.Set Timer Signal different from "OFF", NSeeYouHomeTimer >0 ||
  NTExitLighting >0
  3.VehicleLock Status == RKE Locked || PE Locked
- _Pass criteria: BSeeYouHomeStatus = ON
- _Regression: Yes
- _Time [hr]: 0.4
- _Test environment: Lab-Car (auto)

## STC-BDY02-548: See You Home Activation
See You Home Activation when Right door transition to Open and timer > 0
- _Object type: Nominal Test
- _Status: REVIEWED
- _Procedure: 1.Set NIgnitionStatus=2
  2.Set Timer Signal different from "OFF", NSeeYouHomeTimer >0 ||
  NTExitLighting >0
  3.VehicleLock Status == RKE Locked || PE Locked
- _Pass criteria: BSeeYouHomeStatus = ON
- _Regression: Yes
- _Time [hr]: 0.4
- _Test environment: Lab-Car (auto)

## STC-BDY02-549: See You Home deactivation with Right door open when timer=0
See You Home deactivation when Right door transition to Open and timer = OFF
- _Object type: Negative Test
- _Status: REVIEWED
- _Procedure: 1.Set NIgnitionStatus=2
  2.Set Timer Signal to "OFF", NSeeYouHomeTimer = 0 ||
  NTExitLighting = 0
  3.Right door transitions to an Open status, NDoorROpenStatus = 1
- _Pass criteria: CUHomeActive= False and Dipped Beam=OFF
- _Regression: No
- _Time [hr]: 0.4
- _Test environment: Lab-Car (auto)

## STC-BDY02-550: See You Home deactivation with Left door open when timer=0
See You Home deactivation when Left door transition to Open and timer = OFF
- _Object type: Negative Test
- _Status: REVIEWED
- _Procedure: 1.Set NIgnitionStatus=2
  2.Set Timer Signal to "OFF", NSeeYouHomeTimer = 0 ||
  NTExitLighting = 0
  3.Left door transitions to an Open status, NDoorLOpenStatus = 1
- _Pass criteria: CUHomeActive= False and Dipped Beam=OFF
- _Regression: No
- _Time [hr]: 0.4
- _Test environment: Lab-Car (auto)

## STC-BDY02-551: See You Home deactivation with ignition state transition to 1
See You Home deactivation when ignition state transition to 1 from 2 while CUHome is Active
- _Object type: Nominal Test
- _Status: REVIEWED
- _Procedure: 1.Activate See You Home:
  NIgnitionStatus == Awake &&
  (VehicleLock Status == RKE Locked || PE Locked) &&
  TSeeYouHomeTimer > 0
  2.Do Igniton state transition from 2 to 1, NIgnitionStatus = 1 within timer expires
- _Pass criteria: 1.CUHomeActive= True and Dipped Beam=ON
  2.CUHomeActive= False and Dipped Beam=OFF
- _Regression: No
- _Time [hr]: 0.3
- _Test environment: Lab-Car (auto)

## STC-BDY02-552: See You Home deactivation with ignition state transition >2
See You Home deactivation when ignition state transition >2 while CUHome is Active
- _Object type: Nominal Test
- _Status: REVIEWED
- _Procedure: 1.Activate See You Home:
  NIgnitionStatus == Awake &&
  (VehicleLock Status == RKE Locked || PE Locked) &&
  TSeeYouHomeTimer > 0
  2.Set NIgnitionStatus > 2 within timer expiration
- _Pass criteria: 1.CUHomeActive= True and Dipped Beam=ON
  2.CUHomeActive= False and Dipped Beam=OFF
- _Regression: No
- _Time [hr]: 0.3
- _Test environment: Lab-Car (auto)

## STC-BDY02-553
See You Home deactivation when Car is locked then unlocked again while CUHome is Active
- _Object type: Nominal Test
- _Status: REVIEWED
- _Procedure: 1.Activate See You Home:
  NIgnitionStatus == Awake &&
  (VehicleLock Status == RKE Locked || PE Locked) &&
  TSeeYouHomeTimer > 0
  2.Lock the vehicle and then unlock again within timer expiration
- _Pass criteria: 1.CUHomeActive= True and Dipped Beam=ON
  2.CUHomeActive= False and Dipped Beam=OFF
- _Regression: No
- _Time [hr]: 0.3
- _Test environment: Lab-Car (auto)

## STC-BDY02-554
See You Home deactivation when Car is locked and the Timer expired while CUHome is Active
- _Object type: Nominal Test
- _Status: REVIEWED
- _Procedure: 1.Activate See You Home:
  NIgnitionStatus == Awake &&
  (VehicleLock Status == RKE Locked || PE Locked) &&
  TSeeYouHomeTimer > 0
  2.Lock the vehicle and wait till timer expires
- _Pass criteria: 1.CUHomeActive= True and Dipped Beam=ON
  2.CUHomeActive= False and Dipped Beam=OFF
- _Regression: No
- _Time [hr]: 0.3
- _Test environment: Lab-Car (auto)

## STC-BDY02-1463
See You Home deactivation when vehicle is unlocked(RKE Unlock or PE Unlock) before timeout
- _Object type: Nominal Test
- _Status: REVIEWED
- _Procedure: 1.Activate See You Home:
  NIgnitionStatus == Awake &&
  (VehicleLock Status == RKE Locked || PE Locked) &&
  TSeeYouHomeTimer > 0
  2.Lock the vehicle, NVehicleLockStatus == RKE Unlock || PE Unlock
- _Pass criteria: BSeeYouHomeStatus = OFF (0x0)
- _Regression: No
- _Time [hr]: 0.1
- _Test environment: Lab-Car (auto)

## STC-BDY02-1464: See You Home deactivation when calibratable timer expires
- _Object type: Nominal Test
- _Status: REVIEWED
- _Procedure: 1.Activate See You Home:
  NIgnitionStatus == Awake &&
  (VehicleLock Status == RKE Locked || PE Locked) &&
  TSeeYouHomeTimer > 0
  2.Wait until the calibration timer expires, TSeeYouHomeTimer == 0
- _Pass criteria: BSeeYouHomeStatus = OFF (0x0)
- _Regression: No
- _Time [hr]: 0.2
- _Test environment: Lab-Car (auto)

## STC-BDY02-555: See You Home Temporarily Time
See You Home Temporarily time activation
- _Object type: Nominal Test
- _Status: REVIEWED
- _Procedure: 1.Set NIgnitionStatus = 2
  2.Pull DI Stalk towards the user, NFlashMainSwitch= 0x1
  3.Lock the vehicle using RKE lock button, NVehicleLockStatus = 0x5
  4.Set See You Home Temporarily Time not equal to OFF,
  NSeeYouHomeTimer !=0
- _Pass criteria: See You Home Lighting shall be activated for See You Home Temporarily Time.
  CUHomeTimer = NSeeYouHomeTimer
  See You Home Fixed
  e_x000D_See You Home Temporarily Time Timer (se
  )_x000D_
  f (0
  1 15
  30_x000D_3 45
- _Regression: No
- _Time [hr]: 0.3
- _Test environment: Lab-Car (auto)

## STC-BDY02-556: See You Home Temporarily Time
See You Home Temporarily time activation
- _Object type: Nominal Test
- _Status: REVIEWED
- _Procedure: 1.Set NIgnitionStatus = 2
  2.Pull DI Stalk towards the user, NFlashMainSwitch= 0x1
  3.Lock the vehicle using PE lock button, (NVehicleLockStatus == RKE Lock || PE Lock)
  4.Set See You Home Temporarily Time not equal to OFF, NSeeYouHomeTimer >0 || NTExitLighting >0
- _Pass criteria: See You Home Lighting shall be activated for See You Home Temporarily Time.
  CUHomeTimer = NSeeYouHomeTimer
  See You Home Fixed
  e_x000D_See You Home Temporarily Time Timer (se
  )_x000D_
  f (0
  1 15
  30_x000D_3 45
- _Regression: Yes
- _Time [hr]: 0.3
- _Test environment: Lab-Car (auto)

## STC-BDY02-558
See You Home Temporarily Time shall take precedence over the See You Home Fixed Time when NSeeYouHomeTimer !=0
- _Object type: Nominal Test
- _Status: REVIEWED
- _Procedure: 1.Set NIgnitionStatus = 2
  2.Set See You Home Temporarily Time not equal to OFF,
  NSeeYouHomeTimer !=0 (NTExitLighting !=0)
  3.Lock the vehicle (RKE or PE lock (NVehicleLockStatus = 0x5 || 0x6)
  4.Pull the DI Stalk, NFlashMainSwitch= 0x1 before timer expires
- _Pass criteria: 3. TSeeYouHomeTimer = CUHomeTempTime
  4. See You Home Lighting function activated
- _Regression: Yes
- _Time [hr]: 0.4
- _Test environment: Lab-Car (auto)

## STC-BDY02-477: See You Home Lighting timer
See You Home Lighting timer user configuration
- _Object type: Nominal Test
- _Status: REVIEWED
- _Procedure:
  1. Configure See You Home Lighting timer through the Menu on the driver display using the Menu stalk [ UserConfig::NTExitLighting]
  NTExitLighting Timer (
  )_x000D_
  f (0
  1 15
  30_x000D_3 45
- _Pass criteria: See you home lighting i.e., Dipped beam ON duration shall follow the NSeeYouHomeTimer
- _Regression: No
- _Time [hr]: 0.5
- _Test environment: Lab-Car (auto)

## STC-BDY02-1465: See You Home Temporarily Time increment
See You Home Temporarily Time increment using DIMS stalk
- _Object type: Nominal Test
- _Status: REVIEWED
- _Procedure: 1.NIgnitionStatus == Awake
  2.Pull DIMS stalk towards the steering wheel to a momentary position - first time
  3.Pull DIMS stalk towards the steering wheel to a momentary position - second time
  4.Pull DIMS stalk towards the steering wheel to a momentary position - more than three times
- _Pass criteria: Default:
  CUHomeTempTime = 15 Seconds
  Pull Flash first time:
  CUHomeTempTime = 30 Seconds
  Pull Flash second time:
  CUHomeTempTime = 45 Seconds
  Pull Flash more than three times:
  CUHomeTempTime = 60 Seconds
- _Regression: No
- _Time [hr]: 0.1
- _Test environment: Lab-Car (auto)

## STC-BDY02-1611: Welcome Event activation
Welcome event activation when the vehicle is locked, the passive entry is enable, the keyfob is detected to enter Welcome Zone, the entry lighting is enabled and the battery state of charge is not low
- _Object type: Nominal Test
- _Status: REVIEWED
- _Procedure: BWelcomeEventActive == ON &&
  NTEntryLighting != OFF &&
  NignitionState == LOCKED &&
  NBatteryLowStateOfCharge == OK
- _Pass criteria: BWelcomeEventStatus = ON
  NSideLightLeftStatus = ON
  NSideLightRightStatus = ON
  NTailLightLeftStatus = ON
  NTailLightRightStatus = ON
- _Regression: No
- _Time [hr]: 0.4
- _Test environment: Lab-Car (auto)

## STC-BDY02-1612: Welcome Event deactivation
Welcome event deactivation when Ignition State is greater than Awake (0x2)
- _Object type: Nominal Test
- _Status: REVIEWED
- _Procedure: BWelcomeEventStatus == ON &&
  NignitionState >= Awake
- _Pass criteria: BWelcomeEventStatus = OFF
  NSideLightLeftStatus = OFF
  NSideLightRightStatus = OFF
  NTailLightLeftStatus = OFF
  NTailLightRightStatus = OFF
- _Regression: No
- _Time [hr]: 0.4
- _Test environment: Lab-Car (auto)

## STC-BDY02-1613: Welcome Event deactivation
Welcome event deactivation when the battery state of charge is low
- _Object type: Nominal Test
- _Status: REVIEWED
- _Procedure: BWelcomeEventStatus == ON &&
  NBatteryLowStateOfCharge != OK
- _Pass criteria: BWelcomeEventStatus = OFF
  NSideLightLeftStatus = OFF
  NSideLightRightStatus = OFF
  NTailLightLeftStatus = OFF
  NTailLightRightStatus = OFF
- _Regression: No
- _Time [hr]: 0.4
- _Test environment: Lab-Car (auto)

## STC-BDY02-1614: Welcome Event deactivation
Welcome Event deactivation when the keyfob is detected to exit Welcome Zone or to stay in Welcome Zone over a timeout
- _Object type: Nominal Test
- _Status: REVIEWED
- _Procedure: BWelcomeEventStatus == ON &&
  BWelcomeEventActive == OFF
- _Pass criteria: BWelcomeEventStatus = OFF
  NSideLightLeftStatus = OFF
  NSideLightRightStatus = OFF
  NTailLightLeftStatus = OFF
  NTailLightRightStatus = OFF
- _Regression: No
- _Time [hr]: 0.4
- _Test environment: Lab-Car (auto)

## STC-BDY02-1615: Welcome Event deactivation
Welcome Event deactivation when ADI communication is in fault
- _Object type: Nominal Test
- _Status: REVIEWED
- _Procedure: BWelcomeEventStatus == ON &&
  ADI communication fault raised
- _Pass criteria: BWelcomeEventStatus = OFF
  NSideLightLeftStatus = OFF
  NSideLightRightStatus = OFF
  NTailLightLeftStatus = OFF
  NTailLightRightStatus = OFF
- _Regression: No
- _Time [hr]: 0.4
- _Test environment: Lab-Car (manual)

## STC-BDY02-1616: Sign Off Event activation
Sign Off Event activation when the door gets open after Ignition State drops to Awake, the exit lighting is enabled and the battery state of charge is not low
- _Object type: Nominal Test
- _Status: REVIEWED
- _Procedure: BSignOffEventActive == ON &&
  NTExitLighting != OFF &&
  NBatteryLowStateOfCharge == OK
- _Pass criteria: BSignOffEventStatus = ON
  NDippedBeamLeftStatus = ON
  NDippedBeamRightStatus = ON
  NSideLightLeftStatus = ON
  NSideLightRightStatus = ON
  NTailLightLeftStatus = ON
  NTailLightRightStatus = ON
- _Regression: Yes
- _Time [hr]: 0.1
- _Test environment: Lab-Car (auto)

## STC-BDY02-1618: Sign Off Event deactivation
Sign Off Event deactivation when Ignition State transits back to Awake above with door closed or keyfob enters back to Welcome Zone or vehicle gets unlock from lock again
- _Object type: Nominal Test
- _Status: REVIEWED
- _Procedure: BSignOffEventStatus = ON &&
  BSignOffEventActive == OFF
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF
- _Regression: Yes
- _Time [hr]: 0.1
- _Test environment: Lab-Car (auto)

## STC-BDY02-1619: Sign Off Event deactivation
Sign Off Event deactivation when the battery state of charge is low
- _Object type: Nominal Test
- _Status: REVIEWED
- _Procedure: BSignOffEventStatus = ON &&
  NBatteryLowStateOfCharge != OK
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF
- _Regression: Yes
- _Time [hr]: 0.1
- _Test environment: Lab-Car (auto)

## STC-BDY02-1620: Sign Off Event deactivation
Sign Off Event deactivation when the exit lighting is disable on central display
- _Object type: Nominal Test
- _Status: REVIEWED
- _Procedure: BSignOffEventStatus = ON &&
  NTExitLighting == OFF
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF
- _Regression: Yes
- _Time [hr]: 0.1
- _Test environment: Lab-Car (auto)

## STC-BDY02-1621: Sign Off Event deactivation
Sign Off Event deactivation when the exit lighting timer is reached
- _Object type: Nominal Test
- _Status: REVIEWED
- _Procedure: BSignOffEventStatus = ON &&
  NTExitLighting timer reached
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF
- _Regression: Yes
- _Time [hr]: 0.1
- _Test environment: Lab-Car (auto)

## STC-BDY02-1622: Sign Off Event lighting function timer
Sign Off Event lighting function timer shall be able to be configured by the user via Menu Stalk or contact screen
- _Object type: Nominal Test
- _Status: REVIEWED
- _Procedure: Central display exit lighting settings
- _Pass criteria: NTExitLighting
- _Regression: Yes
- _Time [hr]: 0.1
- _Test environment: Vehicle (static)

## STC-BDY02-1623
Sign Off Event lighting function activation when the DI Stalk is pulled towards the user, the door gets open after ignition state drops to Awake and the battery state of charge is not low
- _Object type: Nominal Test
- _Status: REVIEWED
- _Procedure: BSignOffEventActive == ON &&
  NFlashMainSwitch == Latched &&
  NBatteryLowStateOfCharge == OK
- _Pass criteria: BSignOffEventStatus = ON
  NDippedBeamLeftStatus = ON
  NDippedBeamRightStatus = ON
  NSideLightLeftStatus = ON
  NSideLightRightStatus = ON
  NTailLightLeftStatus = ON
  NTailLightRightStatus = ON
- _Regression: Yes
- _Time [hr]: 0.1
- _Test environment: Lab-Car (auto)

## STC-BDY02-1624: Exit lighting timer
The default exit lighting timer shall be 15s and be able to increase by 15s up to 60s maximum every time when pulling the DI stalk towards the steering wheel to a momentary position with Ignition state on Awake (0x2).
- _Object type: Nominal Test
- _Status: REVIEWED
- _Procedure: NIgnitionStatus == Awake &&
  NFlashMainSwitch == Flash
- _Pass criteria: NTExitLighting starts from 15s and increases by 15s up to 60s
- _Regression: Yes
- _Time [hr]: 0.1
- _Test environment: Vehicle (static)

## STC-BDY02-1625: Sign Off Event deactivation
Sign Off Event deactivation when ADI communication is in fault
- _Object type: Nominal Test
- _Status: REVIEWED
- _Procedure: BSignOffEventActive == ON &&
  ADI communication fault raised
- _Pass criteria: BSignOffEventActive = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.1
- _Test environment: Vehicle (static)

## STC-BDY02-1138: DTRL deactivation with ignition state
To confirm DTRL deactivation when ignition state < 5
- _Object type: Nominal Test
- _Status: REVIEWED
- _Procedure: 1.Set NIgnitionStatus == Ignition (0x5)
  2.Activate DTRL function(DTRL Function available
  && NMasterLightSwitchPosition == OFF && NDippedBeamLeftStatus == Inactive && NDippedBeamRightStatus == Inactive)
  3.Set NIgnitionStatus !== Ignition (0x5)
- _Pass criteria: NDTRLLeftStatus = InActive NDTRLRightStatus = InActive
- _Regression: No
- _Time [hr]: 0.1
- _Test environment: Lab-Car (auto)

## STC-BDY02-217: DTRL control logic - Right Indicator ON (ID:STC-HMI01-204)
DTRL of the right hand shall be deactivated when right hand directional indicator is active
- _Object type: Cross Functional Test
- _Status: REVIEWED
- _Procedure: 1.NHazardStatus = 0x0 && NIndicatorLStatus =0x0 && NIndicatorRStatus = 0x0
  2.Set ignition status ≥ 5 && Master Light Switch Position = 0 || A
  3.Set NIndicatorRStatus = 0x1
  4.Set NIndicatorRStatus = 0x0
- _Pass criteria: 2.DTRL is active.
  NDTRLLeftStatus = (0x1) && NDTRLRightStatus = (0x1),
  NTailLightLeftStatus = (0x1) && NTailLightRightStatus = (0x1),
  NMasterLightStatus = (0x1)
  3.DTRL of the left hand is inactive.
  NDTRLLeftStatus = (0x1) && NDTRLRightStatus = (0x0),
  NTailLightLeftStatus = (0x1) && NTailLightRightStatus = (0x1),NMasterLightStatus = (0x1)
  4.DTRL is active.
  NDTRLLeftStatus = (0x1) && NDTRLRightStatus = (0x1),NMasterLightStatus = (0x1)
- _Regression: Yes
- _Time [hr]: 0.2
- _Test environment: Lab-Car (auto)

## STC-BDY02-225: DTRL control logic - Left Indicator ON
DTRL of the left hand shall be deactivated when left hand directional indicator is active
- _Object type: Nominal Test
- _Status: REVIEWED
- _Procedure: 1.NHazardStatus = 0x0 && NIndicatorLStatus =0x0 && NIndicatorRStatus = 0x0
  2.Set ignition status ≥ 5 && Master Light Switch Position = 0 || A
  3.Set NIndicatorLStatus = 0x1
  4.Set NIndicatorLStatus = 0x0
- _Pass criteria: 2.DTRL is active.
  NDTRLLeftStatus = (0x1) && NDTRLRightStatus = (0x1),
  NTailLightLeftStatus = (0x1) && NTailLightRightStatus = (0x1),
  NMasterLightStatus = (0x1)
  3.DTRL of the left hand is inactive.
  NDTRLLeftStatus = (0x0) && NDTRLRightStatus = (0x1),
  NMasterLightStatus = (0x1),
  NTailLightLeftStatus = (0x1) && NTailLightRightStatus = (0x1)
  4.DTRL is active.
  NDTRLLeftStatus = (0x1) && NDTRLRightStatus = (0x1),NMasterLightStatus = (0x1)
- _Regression: Yes
- _Time [hr]: 0.2
- _Test environment: Lab-Car (auto)

## STC-BDY02-222: DTRL control logic - Hazard ON
DTRL function shall be deactivated when hazard is active
- _Object type: Nominal Test
- _Status: REVIEWED
- _Procedure: 1.NHazardStatus = 0x0 && NIndicatorLStatus =0x0 && NIndicatorRStatus = 0x0
  2.Set ignition status ≥ 5 && Master Light Switch Position = 0 || A
  3.Set NHazardStatus= 0x1
  4.Set NHazardStatus= 0x0
- _Pass criteria: 2.DTRL is active.
  NDTRLLeftStatus = (0x1) && NDTRLRightStatus = (0x1), NTailLightLeftStatus = (0x1) && NTailLightRightStatus = (0x1)
  3.DTRL is inactive.
  NDTRLLeftStatus = (0x0) && NDTRLRightStatus = (0x0),
  NMasterLightStatus = (0x1),
  NTailLightLeftStatus = (0x1) && NTailLightRightStatus = (0x1)
  4.DTRL is active.
  NDTRLLeftStatus = (0x1) && NDTRLRightStatus = (0x1)
- _Regression: Yes
- _Time [hr]: 0.2
- _Test environment: Lab-Car (auto)

## STC-BDY02-1139: DTRL deactivation with MLS position
To confirm DTRL deactivation when Master Light Switch Position is set to Side Light or Dipped Beam position
- _Object type: Nominal Test
- _Status: REVIEWED
- _Procedure: 1.Set NIgnitionStatus == Ignition (0x5)
  2.Activate DTRL function(DTRL Function available
  && NMasterLightSwitchPosition == OFF && NDippedBeamLeftStatus == Inactive && NDippedBeamRightStatus == Inactive)
  3.Set Master Light Switch Position is set to Side Light or Dipped Beam position
- _Pass criteria: NDTRLLeftStatus = InActive NDTRLRightStatus = InActive
- _Regression: No
- _Time [hr]: 0.1
- _Test environment: Lab-Car (auto)

## STC-BDY02-1137: side & tail lamps illumination when DTRL lights are activated
To confirm side & tail lamps illumination when DTRL lights are activated
- _Object type: Nominal Test
- _Status: REVIEWED
- _Procedure: Activate DTRL function(DTRL Function available && NMasterLightSwitchPosition == AUTO
  && NRainLightLSignalError == no error && NLightSwitchRequest == ON && NLightSwitchReason == Daylight)
- _Pass criteria: BLH_HeadlampLEDActivateReq = Active
  BRH_HeadlampLEDActivateReq = Active
  NTailLightLeftStatus = Active
  NTailLightRightStatus = Active
- _Regression: No
- _Time [hr]: 0.1
- _Test environment: Lab-Car (auto)

## STC-BDY02-1142: DTRL Short circuit fault
To confirm DTRL lights diagnostic strategy when short circuit fault occurs
- _Object type: Nominal Test
- _Status: REVIEWED
- _Procedure: 1.Creat DTRL circuit fault i.e., short circuit fault
  2.After fault, make sure the drive feedback curent is out of normal operation thresholds
- _Pass criteria: NLHFrontLampActiveSts = DTRLLampInactive
  NRHFrontLampActiveSts = DTRLLampInactive
  2.A DTC shall be raised
  3.NDTRLClusterMessage = Fault
- _Regression: No
- _Time [hr]: 0.1
- _Test environment: Lab-Car (auto)

## STC-BDY02-1143: DTRL open circuit fault
To confirm DTRL lights diagnostic strategy when open circuit fault occurs
- _Object type: Nominal Test
- _Status: REVIEWED
- _Procedure: 1.Creat DTRL circuit fault i.e., open circuit fault
  2.After fault, make sure the drive feedback curent is out of normal operation thresholds
- _Pass criteria: NLHFrontLampActiveSts = DTRLLampInactive
  NRHFrontLampActiveSts = DTRLLampInactive
  2.A DTC shall be raised
  3.NDTRLClusterMessage = Fault
- _Regression: No
- _Time [hr]: 0.1
- _Test environment: Lab-Car (auto)

## STC-BDY02-1144: DTRL circuit circuit fault reset
To confirm DTRL lights fault reset with new ignition cycle
- _Object type: Nominal Test
- _Status: REVIEWED
- _Procedure: 1.Creat DTRL circuit fault i.e., Open circuit fault
  2.After fault, make sure the drive feedback curent is out of normal operation thresholds
  3.Start new ignition cycle
- _Pass criteria: NLHFrontLampActiveSts = DTRLLampInactive
  NRHFrontLampActiveSts = DTRLLampInactive
- _Regression: No
- _Time [hr]: 0.1
- _Test environment: Lab-Car (auto)

## STC-BDY02-382: Side markers activation for SAE market (ID:STC-CFG01-01-337)
Side markers activation when MLS= 1||2 for SAE market
- _Object type: Cross Functional Test
- _Status: REVIEWED
- _Procedure: 1.Set NVehicleMarket = USA || Canada
  2.Set NIgnitionStatus < 5
  3.Master Light Switch Position = 1 || 2
- _Pass criteria: NFrontLeftSideMarkerActvReq = Active &&
  NRearLeftSideMarkerActvReq = Active &&
  NFrontRightSideMarkerActvReq = Active &&
  NRearRightSideMarkerActvReq = Active
- _Regression: Yes
- _Time [hr]: 0.1
- _Test environment: Lab-Car (auto)

## STC-BDY02-1474: Side markers activation for SAE market
Side markers activation when ign>=5 for SAE market
- _Object type: Nominal Test
- _Status: REVIEWED
- _Procedure: 1.Set NVehicleMarket = USA || Canada
  2.Set NIgnitionStatus == (Ignition (0x5) || Powertrain Activation (0x6))
- _Pass criteria: NFrontLeftSideMarkerActvReq = Active &&
  NRearLeftSideMarkerActvReq = Active &&
  NFrontRightSideMarkerActvReq = Active &&
  NRearRightSideMarkerActvReq = Active
- _Regression: Yes
- _Time [hr]: 0.1
- _Test environment: Lab-Car (auto)

## STC-BDY02-383: Side markers activation for ECE market
Side markers activation with direction indicator function
- _Object type: Nominal Test
- _Status: REVIEWED
- _Procedure: 1.Set NVehicleMarket != (USA || Canada) && INIgnitionStatus ≥ 5
  Case 1:
  NRepeaterLeftOn == Active
  Case 2:
  NRepeaterRightOn == Active
- _Pass criteria: Case 1:
  NFrontLeftSideMarkerActvReq = Active &&
  NRearLeftSideMarkerActvReq = Inactive
  Case 2:
  NFrontRightSideMarkerActvReq= Active &&
  NRearRightSideMarkerActvReq = Inactive
- _Regression: Yes
- _Time [hr]: 0.1
- _Test environment: Lab-Car (auto)

## STC-BDY02-1147: Side marker Short circuit fault
To confirm Side marker lights diagnostic strategy when short circuit fault occurs
- _Object type: Nominal Test
- _Status: REVIEWED
- _Procedure: 1.Creat Side marker circuit fault i.e., short circuit fault
  2.After fault, make sure the drive feedback curent is out of normal operation thresholds
- _Pass criteria: NFrontLeftSideMarkerActiveStatus = Inactive
  NFrontRightSideMarkerActiveStatus = Inactive
  NRearLeftSideMarkerActiveStatus = Inactive
  NRearRightSideMarkerActiveStatus = Inactive
  2.A DTC shall be raised
  3.NSideMarkerClusterMessage = Fault
- _Regression: No
- _Time [hr]: 0.1
- _Test environment: Lab-Car (auto)

## STC-BDY02-1148: Side marker open circuit fault
To confirm Side marker lights diagnostic strategy when open circuit fault occurs
- _Object type: Nominal Test
- _Status: REVIEWED
- _Procedure: 1.Creat Side marker circuit fault i.e., open circuit fault
  2.After fault, make sure the drive feedback curent is out of normal operation thresholds
- _Pass criteria: NFrontLeftSideMarkerActiveStatus = Inactive
  NFrontRightSideMarkerActiveStatus = Inactive
  NRearLeftSideMarkerActiveStatus = Inactive
  NRearRightSideMarkerActiveStatus = Inactive
  2.A DTC shall be raised
  3.NSideMarkerClusterMessage = Fault
- _Regression: No
- _Time [hr]: 0.1
- _Test environment: Lab-Car (auto)

## STC-BDY02-1149: Side marker circuit circuit fault reset
To confirm Side marker lights fault reset with new ignition cycle
- _Object type: Nominal Test
- _Status: REVIEWED
- _Procedure: 1.Creat Side marker circuit fault i.e., Open circuit fault
  2.After fault, make sure the drive feedback curent is out of normal operation thresholds
  3.Start new ignition cycle
- _Pass criteria: NFrontLeftSideMarkerActiveStatus = Inactive
  NFrontRightSideMarkerActiveStatus = Inactive
  NRearLeftSideMarkerActiveStatus = Inactive
  NRearRightSideMarkerActiveStatus = Inactive
- _Regression: No
- _Time [hr]: 0.1
- _Test environment: Lab-Car (auto)

## STC-BDY02-1476: Brake light activation
To confirm brake lights activation with ignition
- _Object type: Nominal Test
- _Status: REVIEWED
- _Procedure: 1.Set NIgnitionStatus == PT Wake || Ignition || Powertrain Activation
  2.Press brake pedal:
  NBrakepedalStatus_Q == Valid && NBrakepedalStatus == Pressed
- _Pass criteria: NBrakeLightLStatus = Active
  NBrakeLightRStatus = Active
  NBrakeLightMiddleStatus = Active
- _Regression: Yes
- _Time [hr]: 0.1
- _Test environment: Lab-Car (auto)

## STC-BDY02-1478: Brake light activation
To confirm brake lights activation when quality signal is Faulty
- _Object type: Nominal Test
- _Status: REVIEWED
- _Procedure: 1.Set NIgnitionStatus == PT Wake || Ignition || Powertrain Activation
  2.Brake pedal quality signal is Faulty and Press brake pedal,
  NBrakepedalStatus_Q != Valid && NpBrake_Q == Valid && pBrake >= pBrakeThresholdActive
- _Pass criteria: NBrakeLightLStatus = Active
  NBrakeLightRStatus = Active
  NBrakeLightMiddleStatus = Active
- _Regression: No
- _Time [hr]: 0.1
- _Test environment: Lab-Car (auto)

## STC-BDY02-1479: Brake light activation
To confirm brake lights activation when quality signal and brake threshold both are Faulty
- _Object type: Nominal Test
- _Status: REVIEWED
- _Procedure: 1.Set NIgnitionStatus == PT Wake || Ignition || Powertrain Activation
  2.Brake pedal quality signal and brake threshold both are Faulty,
  NBrakepedalStatus_Q != Valid && NpBrake_Q != Valid
- _Pass criteria: NBrakeLightLStatus = Active
  NBrakeLightRStatus = Active
  NBrakeLightMiddleStatus = Active
- _Regression: No
- _Time [hr]: 0.1
- _Test environment: Lab-Car (auto)

## STC-BDY02-1151: Brake light activation with ESP request
To confirm brake lights activation when ESP requested
- _Object type: Nominal Test
- _Status: REVIEWED
- _Procedure: 1.Set NIgnitionStatus == PT Wake || Ignition || Powertrain Activation
  2.ESP requests brake light illumination, NDynBrkActive == Active || NBrakeLightRequest == Active
- _Pass criteria: Brake Light illumination shall be 100% pwm
- _Regression: No
- _Time [hr]: 0.1
- _Test environment: Lab-Car (auto)

## STC-BDY02-1480: Brake light activation
To confirm brake lights activation when ESP requested
- _Object type: Nominal Test
- _Status: REVIEWED
- _Procedure: 1.Set NIgnitionStatus == PT Wake || Ignition || Powertrain Activation
  2.Set NDynBrkActive == Active || NRWUActive == Active
- _Pass criteria: NBrakeLightLStatus = Active
  NBrakeLightRStatus = Active
  NBrakeLightMiddleStatus = Active
- _Regression: No
- _Time [hr]: 0.1
- _Test environment: Lab-Car (auto)

## STC-BDY02-1481: Brake light activation
To confirm brake lights activation when NgLongitudinal in Fault
- _Object type: Nominal Test
- _Status: REVIEWED
- _Procedure: 1.Set NIgnitionStatus == PT Wake || Ignition || Powertrain Activation
  2.Set NgLongitudinal_Q != Valid
- _Pass criteria: NBrakeLightLStatus = Active
  NBrakeLightRStatus = Active
  NBrakeLightMiddleStatus = Active
- _Regression: No
- _Time [hr]: 0.1
- _Test environment: Lab-Car (auto)

## STC-BDY02-415: Brake light function activation
Brake lights shall illuminate when deceleration rate is above 0.9 m/s2
- _Object type: Nominal Test
- _Status: REVIEWED
- _Procedure: 1.NIgntionState>=4
  2.Decelerate vehicle at the rate of change of wheel speed(nWheelFL,
  nWheelFR) is above 1.2 m/s2
- _Pass criteria: Brake lights shall be illuminated as long as the deceleration rate is above 0.9 m/s2.
  NBrakeLightLStatus =0x1
  NBrakeLightRStatus = 0x1
  NBrakeLightMiddleStatus =0x1
- _Regression: No
- _Time [hr]: 0.1
- _Test environment: Lab-Car (auto)

## STC-BDY02-419: Brake light function activation
Brake lights shall illuminate when deceleration rate is 1.0m/s2
- _Object type: Nominal Test
- _Status: REVIEWED
- _Procedure: 1.NIgntionState>=4
  2.Decelerate vehicle at the rate of change of wheel speed(nWheelFL,
  nWheelFR) is equal to 1.0m/s2
- _Pass criteria: Brake lights shall be illuminated as long as the deceleration rate is above 0.9 m/s2.
  NBrakeLightLStatus =0x1
  NBrakeLightRStatus = 0x1
  NBrakeLightMiddleStatus =0x1
- _Regression: No
- _Time [hr]: 0.1
- _Test environment: Lab-Car (auto)

## STC-BDY02-1482: Brake light function deactivation
To confirm brake lights deactivation when brake is released
- _Object type: Nominal Test
- _Status: REVIEWED
- _Procedure: 1.Set NIgnitionStatus == PT Wake || Ignition || Powertrain Activation
  2.NBrakepedalStatus_Q == Valid && NBrakepedalStatus != Pressed
- _Pass criteria: NBrakeLightLStatus = Inactive
  NBrakeLightRStatus = Inactive
  NBrakeLightMiddleStatus = Inactive
- _Regression: No
- _Time [hr]: 0.1
- _Test environment: Lab-Car (auto)

## STC-BDY02-1483: Brake light function deactivation
To confirm brake lights deactivation when ESP not requested the brake light
- _Object type: Nominal Test
- _Status: REVIEWED
- _Procedure: 1.Set NIgnitionStatus == PT Wake || Ignition || Powertrain Activation
  2.NDynBrkActive == Inactive &&
  NRWUActive == Inactive
- _Pass criteria: NBrakeLightLStatus = Inactive
  NBrakeLightRStatus = Inactive
  NBrakeLightMiddleStatus = Inactive
- _Regression: No
- _Time [hr]: 0.1
- _Test environment: Lab-Car (auto)

## STC-BDY02-1484: Brake light function deactivation
To confirm brake lights deactivation when brake is released
- _Object type: Nominal Test
- _Status: REVIEWED
- _Procedure: 1.Set NIgnitionStatus == PT Wake || Ignition || Powertrain Activation
  2.NBrakepedalStatus_Q != Valid && NpBrake_Q == Valid && pBrake < pBrakeThresholdInactive
- _Pass criteria: NBrakeLightLStatus = Inactive
  NBrakeLightRStatus = Inactive
  NBrakeLightMiddleStatus = Inactive
- _Regression: No
- _Time [hr]: 0.1
- _Test environment: Lab-Car (auto)

## STC-BDY02-1485: Brake light function deactivation
To confirm brake lights deactivation when gLong < gLongDeactiveThreshold
- _Object type: Nominal Test
- _Status: REVIEWED
- _Procedure: 1.Set NIgnitionStatus == PT Wake || Ignition || Powertrain Activation
  2.NBrakeLightRequest == Inactive && NgLongitudinal_Q == Valid && gLong < gLongDeactiveThreshold (0.9m/s2)
- _Pass criteria: NBrakeLightLStatus = Inactive
  NBrakeLightRStatus = Inactive
  NBrakeLightMiddleStatus = Inactive
- _Regression: No
- _Time [hr]: 0.1
- _Test environment: Lab-Car (auto)

## STC-BDY02-420: Brake light function inactive
Brake lights shall illuminate when deceleration rate is 0.9m/s2
- _Object type: Nominal Test
- _Status: REVIEWED
- _Procedure: 1.NIgntionState>=4
  2.Decelerate vehicle at the rate of change of wheel speed(nWheelFL,
  nWheelFR) is equal to 0.9m/s2
- _Pass criteria: Brake lights shall be inactive as long as the deceleration rate is <=0.9 m/s2.
  NBrakeLightLStatus =0x0
  NBrakeLightRStatus = 0x0
  NBrakeLightMiddleStatus =0x0
- _Regression: No
- _Time [hr]: 0.1
- _Test environment: Lab-Car (auto)

## STC-BDY02-1152: CHMS illumination with Brake light activation
To confirm CHMS illumination with brake lights activation
- _Object type: Nominal Test
- _Status: REVIEWED
- _Procedure: Activate brake lights, NBrakeLightLStatus == Active
  NBrakeLightRStatus == Active
  NBrakeLightMiddleStatus == Active
- _Pass criteria: NRHTailLampActivate_Req = Active
  NLHTailLampActivate_Req = Active
  BCHMS_LampActivateReq = Active
- _Regression: No
- _Time [hr]: 0.1
- _Test environment: Lab-Car (auto)

## STC-BDY02-1153: Brake light activation with 100% PWM
To confirm brake lights activation with 100% PWM
- _Object type: Nominal Test
- _Status: REVIEWED
- _Procedure: Activate brake lights, NBrakeLightLStatus == Active
  NBrakeLightRStatus == Active
  NBrakeLightMiddleStatus == Active
- _Pass criteria: NRHTailLampActivate_Req = Active
  NLHTailLampActivate_Req = Active
  BCHMS_LampActivateReq = Active
  NTailInboardLampIntensity_Req 100%NTailOutboardLampIntensity_Req = 100%
- _Regression: No
- _Time [hr]: 0.1
- _Test environment: Lab-Car (auto)

## STC-BDY02-1159: CHMS Short circuit fault
To confirm CHMS lights diagnostic strategy when short circuit fault occurs
- _Object type: Nominal Test
- _Status: REVIEWED
- _Procedure: 1.Creat CHMS circuit fault i.e., short circuit fault , NCHMS_LampActiveStatus = Fault
  2.After fault, make sure the drive feedback curent is out of normal operation thresholds
- _Pass criteria: NCHMS_LampActiveStatus = Inactive
  2.A DTC shall be raised
  3.NCHMSLightClusterMessage = Fault
- _Regression: No
- _Time [hr]: 0.1
- _Test environment: Lab-Car (auto)

## STC-BDY02-1160: CHMS open circuit fault
To confirm CHMS lights diagnostic strategy when open circuit fault occurs
- _Object type: Nominal Test
- _Status: REVIEWED
- _Procedure: 1.Creat CHMS circuit fault i.e., open circuit fault , NCHMS_LampActiveStatus = Fault
  2.After fault, make sure the drive feedback curent is out of normal operation thresholds
- _Pass criteria: NCHMS_LampActiveStatus = Inactive
  2.A DTC shall be raised
  3.NCHMSLightClusterMessage = Fault
- _Regression: No
- _Time [hr]: 0.1
- _Test environment: Lab-Car (auto)

## STC-BDY02-1161: CHMS circuit circuit fault reset
To confirm CHMS lights fault reset with new ignition cycle
- _Object type: Nominal Test
- _Status: REVIEWED
- _Procedure: 1.Creat CHMS circuit fault i.e., Open circuit fault, NCHMS_LampActiveStatus = Fault
  2.After fault, make sure the drive feedback curent is out of normal operation thresholds
  3.Start new ignition cycle
- _Pass criteria: NCHMS_LampActiveStatus = Inactive
- _Regression: No
- _Time [hr]: 0.1
- _Test environment: Lab-Car (auto)

## STC-BDY02-411: Hazard light function activation (ID:STC-ADA02-04-257)
Hazard function activation with hazard switch
- _Object type: Cross Functional Test
- _Status: REVIEWED
- _Procedure: 1.Set NIgnitionStatus >=0
  2.Press hazard switch, NHazardStatus =HAZARD_REQUEST
- _Pass criteria: Haazard light function shall be activated.
  NIndicatorLOn = Active &&
  NIndicatorROn = Active &&
  NRepeaterLeftOn= Active&&
  NRepeaterRightOn= Active&&
  HazardLightButtonIlumination= ON
- _Regression: Yes
- _Time [hr]: 0.2
- _Test environment: Lab-Car (auto)

## STC-BDY02-412: Hazard light function deactivation
Hazard function deactivation with hazard switch
- _Object type: Nominal Test
- _Status: REVIEWED
- _Procedure: 1.Activate hazard light function:
  Set NIgnitionStatus>=0 && NHazardStatus =HAZARD_REQUEST
  2.Again press hazard switch,NHazardStatus =HAZARD_REQUEST
- _Pass criteria: Haazard light function shall be deactivated.
  NIndicatorLOn = InActive &&
  NIndicatorROn = InActive &&
  NRepeaterLeftOn= InActive&&
  NRepeaterRightOn= InActive&&
  HazardLightButtonIlumination= OFF
- _Regression: Yes
- _Time [hr]: 0.2
- _Test environment: Lab-Car (auto)

## STC-BDY02-409: Hazard light function activated when crash is detected
Hazard function activation when crash is detected
- _Object type: Nominal Test
- _Status: REVIEWED
- _Procedure: 1.Set NIgnitionStatus >=0
  2.Set BCrashDetectHazardsON == Enabled && NCrashSeverity == Low Severity || High Severity
  3. Check NHazardStatus
- _Pass criteria: NHazardStatus = Active
- _Regression: Yes
- _Time [hr]: 0.2
- _Test environment: Lab-Car (auto)

## STC-BDY02-1162: Hazard light function deactivation when crash is detected
Hazard function deactivation when crash is detected
- _Object type: Nominal Test
- _Status: REVIEWED
- _Procedure: 1.Set NIgnitionStatus >=0
  2.Enable crash detection,
  CrashDetectHazardsON =1
  3.Press Hazard switch, NHazardSwitchPressStatus == Pressed
- _Pass criteria: NHazardStatus = Inactive
- _Regression: Yes
- _Time [hr]: 0.2
- _Test environment: Lab-Car (auto)

## STC-BDY02-1168: Emergency braking function activated
Emergency braking function activated when deceleration >= 6 m/s2 and vehicle speed >= 50 kph
- _Object type: Cross Functional Test
- _Status: REVIEWED
- _Procedure:
  1. Set NIgnitionStatus >= 5
  2. Set Vehicle deceleration >= 6 m/s2 && vehicle speed >= 50 kph
- _Pass criteria: To verify that EmergencyBrakeIndication == ON
- _Regression: No
- _Time [hr]: 0.2
- _Test environment: Lab-Car (auto)

## STC-BDY02-1169: Rear lamp stop and CHMS flash at 4 Hz
Rear lamp stop and CHMS flash at 4 Hz when the emergency braking function is active
- _Object type: Nominal Test
- _Status: REVIEWED
- _Procedure: Set NIgnitionStatus >= 5 && EmergencyBrakeIndication == ON
- _Pass criteria: To verify that Brake light && Central High Mounted Stop Lamp (CHMSL) flash at 4 Hz
- _Regression: No
- _Time [hr]: 0.2
- _Test environment: Lab-Car (auto)

## STC-BDY02-1636: Emergency braking switching off (deceleration)
If the emergency braking is active and the vehicle deceleration drops to <= 3.0 m/s2, the emergency braking should switch off
- _Object type: Nominal Test
- _Status: REVIEWED
- _Procedure: 1.EmergencyBrakeIndication == ON
  2.Vehicle deceleration <= 3 m/s2
- _Pass criteria: 2. EmergencyBrakeIndication == OFF
- _Regression: No
- _Time [hr]: 0.2
- _Test environment: Lab-Car (manual)

## STC-BDY02-1637: Emergency braking recovery
If the vehicle speed at the moment the emergency braking is deactivated s >=30 kph, normal lighting logic/behaviours applies
- _Object type: Nominal Test
- _Status: REVIEWED
- _Procedure: 1.EmergencyBrakeIndication == ON
  2.Vehicle deceleration <= 3 m/s2
  3. vehicle speed >= 30 kph
- _Pass criteria: 3.vehicle speed >= 30 kph
- _Regression: No
- _Time [hr]: 0.2
- _Test environment: Lab-Car (manual)

## STC-BDY02-1170: Hazard light deactivation in emergency braking when BEmergencyBrakeIndication == OFF (ID:STC-CFG02-01-1170)
To confirm Hazard light deactivation in emergency braking when BEmergencyBrakeIndication == OFF
- _Object type: Cross Functional Test
- _Status: REVIEWED
- _Procedure: 1.Set NIgnitionStatus >=2
  2.Disbale Emergency hazard function is turned to ON via User Preference in ICU, BEmergencyBrakeIndication == OFF
  3.Give brake pressure greater than threshold, pBrake >PEmergencyBrake
- _Pass criteria: NHazardStatus = Inactive
- _Regression: No
- _Time [hr]: 0.2
- _Test environment: Lab-Car (auto)

## STC-BDY02-1486: Hazard and panic alarm mode activation
To confirm Hazard and panic alarm mode activation when high voltage warning is activated
- _Object type: Nominal Test
- _Status: REVIEWED
- _Procedure: 1.Set NIgnitionStatus >=2
  2.Activate high voltage warning by Hybrid system with debouncing,
  BHybridHVWarnRequest == ON
  3.Press Hazard switch
- _Pass criteria: 2.NHazardStatus = Active
  NPanicModeActivated = Active
  DTC raised
  3.NHazardStatus == Inactive
  NPanicModeActivated == Inactive
- _Regression: No
- _Time [hr]: 0.1
- _Test environment: Lab-Car (auto)

## STC-BDY02-1487: Hazard and panic alarm mode deactivation
To confirm Hazard and panic alarm mode deactivation when high voltage warning is deactivated
- _Object type: Nominal Test
- _Status: REVIEWED
- _Procedure: 1.Set NIgnitionStatus >=2
  2.Activate high voltage warning by Hybrid system with debouncing,
  BHybridHVWarnRequest == ON
  3.High voltage warning is dismissed
- _Pass criteria: NHazardStatus == Inactive
  NPanicModeActivated == Inactive
- _Regression: No
- _Time [hr]: 0.1
- _Test environment: Lab-Car (auto)

## STC-BDY02-1172: Hazard switch button illumination and flashing during Hazard light activation
To confirm Hazard switch button illumination and flashing during Hazard light activation
- _Object type: Nominal Test
- _Status: REVIEWED
- _Procedure: 1.Set NIgnitionStatus >=2
  2.Enable Hazard with Emergency braking, NHazardStatus = active(pBrake >PEmergencyBrake && BEmergencyBrakeIndication == OFF)
- _Pass criteria: Hazard switch button shall be illuminated and flashing at 1.5 Hz frequency
- _Regression: No
- _Time [hr]: 0.2
- _Test environment: Lab-Car (auto)

## STC-BDY02-1171: Exterior lights flash frequency and Duty cycle during Hazard light activation
To confirm Exterior lights flash frequency and Duty cycle during Hazard light activation
- _Object type: Nominal Test
- _Status: REVIEWED
- _Procedure: 1.Set NIgnitionStatus >=2
  2.Enable Hazard with Emergency braking, NHazardStatus = active(pBrake >PEmergencyBrake && BEmergencyBrakeIndication == OFF)
- _Pass criteria: All exterior lights shall flash at 1.5Hz frequency with 50% duty cycle, NIndicatorLOn = Flash
  NIndicatorROn = Flash
  NRepeaterLeftOn = Flash
  NRepeaterRightOn = Flash
  NRHTailLampActivate_Req = Flash
  NLHTailLampActivate_Req = Flash
  HazardLightButtonIlumination= Flash
  Tell-tales displayed in flash
  Audible warning sounded
- _Regression: No
- _Time [hr]: 0.2
- _Test environment: Lab-Car (auto)

## STC-BDY02-1174: Exterior lights flash frequency and Duty cycle during Hazard light activation in ignition state <2
To confirm Exterior lights flash frequency and Duty cycle during Hazard light activation in ignition state <2
- _Object type: Nominal Test
- _Status: REVIEWED
- _Procedure: 1.Set NIgnitionStatus < 2
  2.Enable Hazard with Emergency braking, NHazardStatus = active(pBrake >PEmergencyBrake && BEmergencyBrakeIndication == OFF)
- _Pass criteria: Flashing at the same frequency:
  NIndicatorLOn = Flash
  NIndicatorROn = Flash
  NRepeaterLeftOn = Flash
  NRepeaterRightOn = Flash
  NRHTailLampActivate_Req = Flash
  NLHTailLampActivate_Req = Flash
  HazardLightButtonIlumination= Flash
- _Regression: No
- _Time [hr]: 0.2
- _Test environment: Lab-Car (auto)

## STC-BDY02-1165: Hazard light Short circuit fault
To confirm Hazard lights diagnostic strategy when short circuit fault occurs
- _Object type: Nominal Test
- _Status: REVIEWED
- _Procedure: 1.Creat Hazard light circuit fault i.e., short circuit fault
  2.After fault, make sure the drive feedback curent is out of normal operation thresholds
- _Pass criteria: NHazardSwitchPressStatus = Unpressed
  2.A DTC shall be raised
  3.NHazardCtrlClusterMessage = Fault
- _Regression: No
- _Time [hr]: 0.1
- _Test environment: Lab-Car (auto)

## STC-BDY02-1166: Hazard light open circuit fault
To confirm Hazard lights diagnostic strategy when open circuit fault occurs
- _Object type: Nominal Test
- _Status: REVIEWED
- _Procedure: 1.Creat Hazard light circuit fault i.e., open circuit fault
  2.After fault, make sure the drive feedback curent is out of normal operation thresholds
- _Pass criteria: NHazardSwitchPressStatus = Unpressed
  2.A DTC shall be raised
  3.NHazardCtrlClusterMessage = Fault
- _Regression: No
- _Time [hr]: 0.1
- _Test environment: Lab-Car (auto)

## STC-BDY02-1167: Hazard light circuit circuit fault reset
To confirm Hazard lights fault reset with new ignition cycle
- _Object type: Nominal Test
- _Status: REVIEWED
- _Procedure: 1.Creat Hazard light circuit fault i.e., Open circuit fault
  HSD11_2 = Open circuit or short to Gnd
  2.After fault, make sure the drive feedback curent is out of normal operation thresholds
  3.Start new ignition cycle
- _Pass criteria: NHazardSwitchPressStatus = Unpressed
- _Regression: No
- _Time [hr]: 0.1
- _Test environment: Lab-Car (auto)

## STC-BDY02-1638: Hazard Light Button DTC
The hazard button illumination shall be driven by a PWM HSD by the domain controller, so if a fault is detected a DTC shall be raised.
- _Object type: Nominal Test
- _Status: REVIEWED
- _Procedure: 1.Creat Hazard light circuit fault i.e., Open circuit fault
  HSD11_2 = Open circuit or short to Gnd
  2. Press the hazard button
- _Pass criteria: 2. DTC raised
- _Regression: No
- _Time [hr]: 0.2
- _Test environment: Lab-Car (manual)

## STC-BDY02-1175: Right Directional Indicator Activation
To confirm Right Directional Indicator Activation when DIMS stalk is pushed Upwards
- _Object type: Nominal Test
- _Status: REVIEWED
- _Procedure: 1.Set NIgnitionStatus == (Ignition || Powertrain Activation)
  2.Puh DIMS stalk Upwards, NDISwitch == Upwards
- _Pass criteria: NIndicatorRStatus = Active
- _Regression: No
- _Time [hr]: 0.1
- _Test environment: Lab-Car (auto)

## STC-BDY02-1176: Left Directional Indicator Activation
To confirm Left Directional Indicator Activation when DIMS stalk is pushed Downwards
- _Object type: Nominal Test
- _Status: REVIEWED
- _Procedure: 1.Set NIgnitionStatus == (Ignition || Powertrain Activation)
  2.Puh DIMS stalk Downwards, NDISwitch == Downwards
- _Pass criteria: NIndicatorLStatus = Active
- _Regression: No
- _Time [hr]: 0.1
- _Test environment: Lab-Car (auto)

## STC-BDY02-1177: Exterior lamps illumination when Right Directional Indicator is Activated
To confirm Exterior lamps illumination when Right Directional Indicator is Activated
- _Object type: Nominal Test
- _Status: REVIEWED
- _Procedure: 1.Set NIgnitionStatus == (Ignition || Powertrain Activation)
  2.Puh DIMS stalk Upwards, NDISwitch == Upwards
- _Pass criteria: NInidcatorROn = Active
  NRepeaterRightOn = Active
  NTailLightRightStatus = Active
- _Regression: No
- _Time [hr]: 0.1
- _Test environment: Lab-Car (auto)

## STC-BDY02-1178: Exterior lamps illumination when Left Directional Indicator is Activated
To confirm Exterior lamps illumination when Left Directional Indicator is Activated
- _Object type: Nominal Test
- _Status: REVIEWED
- _Procedure: 1.Set NIgnitionStatus == (Ignition || Powertrain Activation)
  2.Puh DIMS stalk Downwards, NDISwitch == Downwards
- _Pass criteria: NInidcatorLOn = Active
  NRepeaterLeftOn = Active
  NTailLightLeftStatus = Active
- _Regression: No
- _Time [hr]: 0.1
- _Test environment: Lab-Car (auto)

## STC-BDY02-1179: DI flash frequency with 50%
To confirm DI flash frequency
- _Object type: Nominal Test
- _Status: REVIEWED
- _Procedure: NIndicatorRStatus == Active ||
  NIndicatorLStatus == Active
- _Pass criteria: All related DI lamps flash at 1.5Hz with 50% duty cycle
- _Regression: No
- _Time [hr]: 0.1
- _Test environment: Lab-Car (auto)

## STC-BDY02-1180: Directional Indicator function deactivation with Hazard activation
To confirm DI function deactivation when hazard function is activated
- _Object type: Nominal Test
- _Status: REVIEWED
- _Procedure: 1.Activate Directional Indicator function, NIndicatorRStatus == Active ||
  NIndicatorLStatus == Active
  2.Press Hazard button, NHazardStatus == Active
- _Pass criteria: NIndicatorRStatus = Inactive
  NIndicatorLStatus = Inactive
  after the last flash
- _Regression: No
- _Time [hr]: 0.1
- _Test environment: Lab-Car (auto)

## STC-BDY02-1181: Tell tale display when Directional Indicator function activated
To confirm Tell tale display when Directional Indicator function activated
- _Object type: Nominal Test
- _Status: REVIEWED
- _Procedure: 1.Activate Directional Indicator function, NIndicatorRStatus == Active ||
  NIndicatorLStatus == Active
- _Pass criteria: Direction Indicator function status for the telltale, to indicate a green arrow consistent with the user direction request and an audible warning flash at 1.5 Hz frequency, synchronised with the direction indicator lights
- _Regression: No
- _Time [hr]: 0.1
- _Test environment: Lab-Car (manual)

## STC-BDY02-399: Left Direction indicator no of flashes
Left Direction indicator lights no of flashes equals to DILaneChangeFlashes
- _Object type: Nominal Test
- _Status: REVIEWED
- _Procedure: 1.Set NIgnitionStatus>=5
  2.Turn DIMS stalk left for less than DIMomentaryRequestTime i.e., 2sec(NDISwitch = 1 for <2sec)
- _Pass criteria: DILeftState_Active && Left Direction indicator light number of flashes equal to DILaneChangeFlashes i.e.,3 flashes,
  NInidcatorLOn = Active &&
  NRepeaterLeftOn= Active
- _Regression: Yes
- _Time [hr]: 0.1
- _Test environment: Lab-Car (auto)

## STC-BDY02-404: Right Direction indicator no of flashes
Right Direction indicator lights no of flashes equals to DILaneChangeFlashes
- _Object type: Nominal Test
- _Status: REVIEWED
- _Procedure: 1.Set NIgnitionStatus>=5
  2.Turn DIMS stalk right for less than DIMomentaryRequestTime i.e., 2sec(NDISwitch = 3 for <2sec)
- _Pass criteria: DIRighttState_Active && Right Direction indicator light number of flashes equal to DILaneChangeFlashes i.e.,3 flashes,
  NInidcatorROn = Active &&
  NRepeaterRightOn= Active
- _Regression: Yes
- _Time [hr]: 0.1
- _Test environment: Lab-Car (auto)

## STC-BDY02-405: Left Direction indicator no of flashes
Left Direction indicator lights no of flashes equals to DIMS stalk activation time
- _Object type: Nominal Test
- _Status: REVIEWED
- _Procedure: 1.Set NIgnitionStatus>=5
  2.Turn DIMS stalk left for longer than DIMomentaryRequestTime i.e., 2sec(NDISwitch = 1 for >2sec)
- _Pass criteria: DILeftState_Active && Left Direction indicator light shall flash for the duration DIMS stalk is activated,
  NInidcatorLOn = Active &&
  NRepeaterLeftOn= Active
- _Regression: Yes
- _Time [hr]: 0.1
- _Test environment: Lab-Car (auto)

## STC-BDY02-406: Right Direction indicator no of flashes
Right Direction indicator lights no of flashes equals to DIMS stalk activation time
- _Object type: Nominal Test
- _Status: REVIEWED
- _Procedure: 1.Set NIgnitionStatus>=5
  2.Turn DIMS stalk right for longer than DIMomentaryRequestTime i.e., 2sec(NDISwitch = 3 for >2sec)
- _Pass criteria: DIRighttState_Active && Right Direction indicator light shall flash for the duration DIMS stalk is activated,
  NInidcatorROn = Active &&
  NRepeaterRightOn= Active
- _Regression: Yes
- _Time [hr]: 0.1
- _Test environment: Lab-Car (auto)

## STC-BDY02-400: DIMS input received for opposite direction
Directional indicator function when DIMS input received for opposite direction
- _Object type: Nominal Test
- _Status: REVIEWED
- _Procedure: 1.Enable Left direction indicator light:
  Set NIgnitionStatus>=5 && NDISwitch = 1
  2.Turn DIMS stalk Right (NDISwitch = 3) immediately within no time
- _Pass criteria: Direction indicator function shall be Inactive for PostLaneChangeCancellationDelay i.e.,500ms,
  DIState_Inactive && NInidcatorLOn = InActive && NRepeaterLeftOn= InActive.
  After 500ms,Right direction indicator light shall be active,NInidcatorROn = Active &&
  NRepeaterRightOn= Active,
  NInidcatorLOn = InActive &&
  NRepeaterLeftOn= InActive
- _Regression: Yes
- _Time [hr]: 0.1
- _Test environment: Lab-Car (auto)

## STC-BDY02-407: DIMS input received for opposite direction
Directional indicator function when DIMS input received for opposite direction
- _Object type: Nominal Test
- _Status: REVIEWED
- _Procedure: 1.Enable Right direction indicator light:
  Set NIgnitionStatus >=5 && NDISwitch = 3
  2.Turn DIMS stalk Left(NDISwitch = 1) immediately within no time
- _Pass criteria: Direction indicator function shall be Inactive for PostLaneChangeCancellationDelay i.e.,500ms,
  DIState_Inactive && NInidcatorROn = InActive && NRepeaterRightOn= InActive.
  After 500ms,Left direction indicator light shall be active,NInidcatorLOn = Active &&
  NRepeaterLeftOn= Active,
  NInidcatorROn = InActive &&
  NRepeaterRightOn= InActive
- _Regression: Yes
- _Time [hr]: 0.1
- _Test environment: Lab-Car (auto)

## STC-BDY02-1185: Direction indicator lamps Short circuit fault
To confirm Direction indicator lamps diagnostic strategy when short circuit fault occurs
- _Object type: Nominal Test
- _Status: REVIEWED
- _Procedure: 1.Creat Direction indicator lamps circuit fault i.e., short circuit fault
  2.After fault, make sure the drive feedback curent is out of normal operation thresholds
- _Pass criteria: NFrontIndicatorLONActiveSts = Fault
  NFrontIndicatorRONActiveSts = Fault
  NLHSideRepeaterONSts = Fault
  NRHSideRepeaterONSts = Fault
  NHazardSwitchPressStatus = Unpressed
  2.A DTC shall be raised
  3.NHazardCtrlClusterMessage = Fault
- _Regression: No
- _Time [hr]: 0.1
- _Test environment: Lab-Car (auto)

## STC-BDY02-1186: Direction indicator lampsopen circuit fault
To confirm Direction indicator lamps diagnostic strategy when open circuit fault occurs
- _Object type: Nominal Test
- _Status: REVIEWED
- _Procedure: 1.Creat Direction indicator lamps circuit fault i.e., open circuit fault
  2.After fault, make sure the drive feedback curent is out of normal operation thresholds
- _Pass criteria: NFrontIndicatorLONActiveSts = Fault
  NFrontIndicatorRONActiveSts = Fault
  NLHSideRepeaterONSts = Fault
  NRHSideRepeaterONSts = Fault
  NHazardSwitchPressStatus = Unpressed
  2.A DTC shall be raised
  3.NHazardCtrlClusterMessage = Fault
- _Regression: No
- _Time [hr]: 0.1
- _Test environment: Lab-Car (auto)

## STC-BDY02-1187: Direction indicator lamps circuit circuit fault reset
To confirm Direction indicator lamps fault reset with new ignition cycle
- _Object type: Nominal Test
- _Status: REVIEWED
- _Procedure: 1.Creat Direction indicator lamps circuit fault i.e., Open circuit fault
  2.After fault, make sure the drive feedback curent is out of normal operation thresholds
  3.Start new ignition cycle
- _Pass criteria: LeftIndicatorFault,
  RightIndicatorFault,
  LeftRepeaterFault,
  RightRepeaterFault
- _Regression: No
- _Time [hr]: 0.1
- _Test environment: Lab-Car (auto)

## STC-BDY02-1317: Alarm status indication
To confirm Alarm status indication
- _Object type: Nominal Test
- _Status: REVIEWED
- _Procedure: 1.Set igniton state = any value
  2.NAlarmStatus == Triggered
- _Pass criteria: All the DIs shall Flash at a calibratable frequency AlarmIndicationActive (1.5Hz) and at a duty cycle calibrated AlarmTriggerDuty (50%)
- _Regression: No
- _Time [hr]: 0.2
- _Test environment: Lab-Car (manual)

## STC-BDY02-352: Fog light activation
- _Object type: Nominal Test
- _Status: REVIEWED
- _Procedure: 1.Set ignition status = 5||6
  2.Set MasterLightSwitch = A||2 and press centre button on the Master Light switch
- _Pass criteria: FogLightAvailable = True & Fog light shall illuminate
- _Regression: Yes
- _Time [hr]: 0.1
- _Test environment: Lab-Car (auto)

## STC-BDY02-356: Fog light NOT available
Fog light NOT available when ignition state<5
- _Object type: Nominal Test
- _Status: REVIEWED
- _Procedure: 1.Set ignition status < 5
  2.Set MasterLightSwitch = A||2 and press centre button on the Master Light switch
- _Pass criteria: FogLightAvailable = False & Fog light OFF
- _Regression: No
- _Time [hr]: 0.1
- _Test environment: Lab-Car (auto)

## STC-BDY02-357: Fog light NOT available
Fog light NOT available when Master Light Switch !=A||2
- _Object type: Nominal Test
- _Status: REVIEWED
- _Procedure: 1.Set ignition status = 5||6
  2.Set MasterLightSwitch != A||2 and press centre button on the Master Light switch
- _Pass criteria: FogLightAvailable = False & Fog light OFF
- _Regression: No
- _Time [hr]: 0.1
- _Test environment: Lab-Car (auto)

## STC-BDY02-358: Fog light deactivation
Fog light deactivation by exiting current ignition state
- _Object type: Negative Test
- _Status: REVIEWED
- _Procedure: 1.Activate Fog light(ignition status = 5||6 &&
  MasterLightSwitch = A||2)
  2.Set ignition status < 5
- _Pass criteria: 1.FogLightAvailable = True & Fog light shall illuminate
  2.FogLightAvailable = False & Fog light OFF
- _Regression: No
- _Time [hr]: 0.1
- _Test environment: Lab-Car (auto)

## STC-BDY02-359: Fog light deactivation
Fog light deactivation by master light switch
- _Object type: Negative Test
- _Status: REVIEWED
- _Procedure: 1.Activate Fog light(ignition status = 5||6 &&
  MasterLightSwitch = A||2)
  2.Set MasterLightSwitch != A||2
- _Pass criteria: 1.FogLightAvailable = True & Fog light shall illuminate
  2.FogLightAvailable = False & Fog light OFF
- _Regression: No
- _Time [hr]: 0.1
- _Test environment: Lab-Car (auto)

## STC-BDY02-501: Rear fog light activation
- _Object type: Nominal Test
- _Status: REVIEWED
- _Procedure: 1.Set Ignition state>=5
  2.Rear Fog light is Inactive,
  FogLightAvailable = True && FogLightActive= False
  3.MLS =Auto||Dipped
  4.Press Fog light switch i.e., press the centre button in Master Light Switch (rising edge)
- _Pass criteria: 4.FogLightActive= True, NFogLightRstatus= 0x1.
  Turn on the Fog Light
  Turn on the Dipped Beam.
  NFogLightRstatus =0x1
  NDippedBeamLeftStatus = (0x1)
  NDippedBeamRightStatus = (0x1)
- _Regression: Yes
- _Time [hr]: 0.1
- _Test environment: Lab-Car (auto)

## STC-BDY02-511: Fog light deactivation with ignition state
Fog light deactivation when ignition state is <5
- _Object type: Negative Test
- _Status: REVIEWED
- _Procedure: 1.Activate Rear Fog light :
  FogLightActive= True && NFogLightRstatus= 0x1
  2.Set ignition state <5
- _Pass criteria: 1.IFogLightActive= True
  Turn ON the Fog Light
  Turn ON the Dipped Beam
  2.FogLightActive= False
  Turn Off the Fog Light
  Turn off the Dipped Beam
- _Regression: No
- _Time [hr]: 0.1
- _Test environment: Lab-Car (auto)

## STC-BDY02-512: Fog light deactivation with MLS
Fog light deactivation when
MLS !=Auto|| Dipped
- _Object type: Negative Test
- _Status: REVIEWED
- _Procedure: 1.Activate Rear Fog light :
  FogLightActive= True && NFogLightRstatus= 0x1
  2.Set MLS !=Auto||Dipped
- _Pass criteria: 1.IFogLightActive= True
  Turn ON the Fog Light
  Turn ON the Dipped Beam
  2.FogLightActive= False
  Turn Off the Fog Light
  Turn off the Dipped Beam
- _Regression: No
- _Time [hr]: 0.1
- _Test environment: Lab-Car (auto)

## STC-BDY02-508: Rear fog light deactivation
- _Object type: Nominal Test
- _Status: REVIEWED
- _Procedure: 1.Activate Rear Fog light: FogLightActive= True &&
  Fog Light Switch press(rising edge )
  2.Press Fog light switch again i.e., press the centre button in Master Light Switch (rising edge)
- _Pass criteria: 2.FogLightActive= False
  Turn Off the Fog Light
  Turn off the Dipped Beam.
  NFogLightRstatus =0x0
  NDippedBeamLeftStatus = (0x0)
  NDippedBeamRightStatus = (0x0)
- _Regression: Yes
- _Time [hr]: 0.1
- _Test environment: Lab-Car (auto)

## STC-BDY02-502: Dipped beam kept ON
Dipped beam kept ON while MLS is in Auto position when Fog is activated
- _Object type: Nominal Test
- _Status: REVIEWED
- _Procedure: Activate Rear Fog light while the Master Light Switch is in AUTO position : FogLightActive= True &&
  Fog Light Switch press(rising edge ) && MasterLightSwitch = A
- _Pass criteria: Dipped beam kept ON.
  NDippedBeamLeftStatus = (0x1)
  NDippedBeamRightStatus = (0x1)
- _Regression: No
- _Time [hr]: 0.1
- _Test environment: Lab-Car (auto)

## STC-BDY02-503: Dipped beam with Fog light
Dipped beam while MLS in Auto position and when Fog light is deactivated
- _Object type: Nominal Test
- _Status: REVIEWED
- _Procedure: 1.Activate Rear Fog light while the Master Light Switch is in AUTO position : FogLightActive= True &&
  Fog Light Switch press(rising edge ) && MasterLightSwitch = A
  2.Deactivate the Fog light by pressing the the centre button in Master Light Switch (rising edge)
- _Pass criteria: 2. Dipped beam OFF
- _Regression: No
- _Time [hr]: 0.1
- _Test environment: Lab-Car (auto)

## STC-BDY02-509: Dipped beam with Fog light
Dipped beam while MLS in Side position and when Fog light is activated
- _Object type: Nominal Test
- _Status: REVIEWED
- _Procedure: 1.Activate Rear Fog light while the Master Light Switch is in AUTO position : FogLightActive= True &&
  Fog Light Switch press(rising edge ) && MasterLightSwitch = A
  2.Set Master light switch to Side position
- _Pass criteria: 2. Dipped beam OFF
- _Regression: No
- _Time [hr]: 0.1
- _Test environment: Lab-Car (auto)

## STC-BDY02-1639: Fog Light Lamp
The fog lamp shall be illuminated when the fog light function is activated
- _Object type: Nominal Test
- _Status: REVIEWED
- _Procedure: NFogLightRStatus == Active
- _Pass criteria: NFogLampDrvrStatus = Active
- _Regression: No
- _Time [hr]: 0.1
- _Test environment: Lab-Car (manual)

## STC-BDY02-504: Fog light telltale (ID: STC-HMI01-236)
Fog light telltale activation when Fog lights are active
- _Object type: Cross Functional Test
- _Status: REVIEWED
- _Procedure: Activate Rear Fog light :
  NFogLightRstatus= 0x1
- _Pass criteria: Rear Fog light telltale shall be displayed on driver display
- _Regression: Yes
- _Time [hr]: 0.1
- _Test environment: Lab-Car (manual)

## STC-BDY02-505: Fog light telltale inactive with default value
Rear fog light telltale shall be inactive when fog light signals in default value for 5 times
- _Object type: Nominal Test
- _Status: REVIEWED
- _Procedure: 1.Activate Rear Fog light :
  NFogLightRstatus= 0x1
  2.Simulate Rear Fog light signal as default value(NFogLightRstatus=0x3) and send 5 consecutive times onto the bus
- _Pass criteria: 1.Rear Fog light telltale shall be displayed on driver display
  2.Rear Fog light Telltale shall not be displayed
- _Regression: No
- _Time [hr]: 0.1
- _Test environment: Lab-Car (manual)

## STC-BDY02-506: Fog light telltale inactive with CAN timeout
Rear fog light telltale shall be inactive when CAN timeout occurs on the Rear Fog Light signal
- _Object type: Nominal Test
- _Status: REVIEWED
- _Procedure: 1.Activate Rear Fog light :
  NFogLightRstatus= 0x1
  2.Remove fog light switch in order to stop rear fog light signal for CAN timeout duration
- _Pass criteria: 1.Rear Fog light telltale shall be displayed on driver display
  2.Rear Fog light Telltale shall not be displayed
- _Regression: No
- _Time [hr]: 0.1
- _Test environment: Lab-Car (manual)

## STC-BDY02-510: Fog light switch LED illumination
LED in Fog light switch shall be illuminate when Fog light is active
- _Object type: Nominal Test
- _Status: REVIEWED
- _Procedure: 1.Activate Rear Fog light :
  FogLightActive= True && NFogLightRstatus= 0x1
  2.Deactivate Rear Fog light:
  FogLightActive= False &&NFogLightRstatus= 0x0
- _Pass criteria: 1.Illuminate the Fog Light Switch LED
  2.Deilluminate the Fog Light Switch LED
- _Regression: Yes
- _Time [hr]: 0.1
- _Test environment: Lab-Car (auto)

## STC-BDY02-1190: Fog lamp Short circuit fault
To confirm fog lamp diagnostic strategy when short circuit fault occurs
- _Object type: Nominal Test
- _Status: REVIEWED
- _Procedure: 1.Creat fog lamp circuit fault i.e., short circuit fault , NFogLampDrvrStatus = Fault
  2.After fault, make sure the drive feedback curent is out of normal operation thresholds
- _Pass criteria: NFogLampDrvrStatus = Fault
  2.A DTC shall be raised
  3.NFogLightClusterMessage = Fault
- _Regression: No
- _Time [hr]: 0.1
- _Test environment: Lab-Car (auto)

## STC-BDY02-1191: Fog lamp open circuit fault
To confirm fog lamp diagnostic strategy when open circuit fault occurs
- _Object type: Nominal Test
- _Status: REVIEWED
- _Procedure: 1.Creat fog lamp circuit fault i.e., open circuit fault , NFogLampDrvrStatus = Fault
  2.After fault, make sure the drive feedback curent is out of normal operation thresholds
- _Pass criteria: NFogLampDrvrStatus = Fault
  2.A DTC shall be raised
  3.NFogLightClusterMessage = Fault
- _Regression: No
- _Time [hr]: 0.1
- _Test environment: Lab-Car (auto)

## STC-BDY02-1192: Fog lamp circuit circuit fault reset
To confirm fog lamp fault reset with new ignition cycle
- _Object type: Nominal Test
- _Status: REVIEWED
- _Procedure: 1.Creat fog lamp circuit fault i.e., Open circuit fault, NFogLampDrvrStatus = Fault
  2.After fault, make sure the drive feedback curent is out of normal operation thresholds
  3.Start new ignition cycle
- _Pass criteria: NFogLampDrvrStatus = Inactive
- _Regression: No
- _Time [hr]: 0.1
- _Test environment: Lab-Car (auto)

## STC-BDY02-1194: License plate illumination
To confirm license plate illumination when side || dipped beam is active
- _Object type: Nominal Test
- _Status: REVIEWED
- _Procedure: 1.Activate Side lights or Dipped beam function(Set NIgnitionStatus =2 && NMasterLightStatus == Side Light || Dipped Beam)
- _Pass criteria: BLicenseLampActivateReq = Active && NLHLicenseLampActiveSts = Active
  NRHLicenseLampActiveSts = Active
- _Regression: No
- _Time [hr]: 0.1
- _Test environment: Lab-Car (auto)

## STC-BDY02-1197: License plate illumination deactivation
To confirm license plate illumination deactivation when side || dipped beam is inactive
- _Object type: Nominal Test
- _Status: REVIEWED
- _Procedure: 1.Activate Side lights or Dipped beam function(Set NIgnitionStatus =2 && NMasterLightStatus == Side Light || Dipped Beam)
  2.Inactivate Side lights or Dipped beam function,NMasterLightStatus !== Side Light || Dipped Beam
- _Pass criteria: BLicenseLampActivateReq = Inactive
- _Regression: No
- _Time [hr]: 0.1
- _Test environment: Lab-Car (auto)

## STC-BDY02-1200: License plate lamp Short circuit fault
To confirm license plate lamp diagnostic strategy when short circuit fault occurs
- _Object type: Nominal Test
- _Status: REVIEWED
- _Procedure: 1.Creat license plate lamp circuit fault i.e., short circuit fault , NLHLicenseLampActiveSts = Fault
  OR
  NRHLicenseLampActiveSts = Fault
  2.After fault, make sure the drive feedback curent is out of normal operation thresholds
- _Pass criteria: NLHLicenseLampActiveSts = Inactive
  NRHLicenseLampActiveSts = Inactive
  2.A DTC shall be raised
  3.NLicensePlateClusterMessage = Fault
- _Regression: No
- _Time [hr]: 0.1
- _Test environment: Lab-Car (auto)

## STC-BDY02-1201: License plate lamp open circuit fault
To confirm license plate lamp diagnostic strategy when open circuit fault occurs
- _Object type: Nominal Test
- _Status: REVIEWED
- _Procedure: 1.Creat license plate lamp circuit fault i.e., open circuit fault , NLHLicenseLampActiveSts = Fault
  OR
  NRHLicenseLampActiveSts = Fault
  2.After fault, make sure the drive feedback curent is out of normal operation thresholds
- _Pass criteria: NLHLicenseLampActiveSts = Inactive
  NRHLicenseLampActiveSts = Inactive
  2.A DTC shall be raised
  3.NLicensePlateClusterMessage = Fault
- _Regression: No
- _Time [hr]: 0.1
- _Test environment: Lab-Car (auto)

## STC-BDY02-1202: License plate lamp circuit circuit fault reset
To confirm license plate lamp fault reset with new ignition cycle
- _Object type: Nominal Test
- _Status: REVIEWED
- _Procedure: 1.Creat license plate lamp circuit fault i.e., Open circuit fault, NLHLicenseLampActiveSts = Fault
  OR
  NRHLicenseLampActiveSts = Fault
  2.After fault, make sure the drive feedback curent is out of normal operation thresholds
  3.Start new ignition cycle
- _Pass criteria: NLHLicenseLampActiveSts = Inactive
  NRHLicenseLampActiveSts = Inactive
- _Regression: No
- _Time [hr]: 0.1
- _Test environment: Lab-Car (auto)

## STC-BDY02-1209: Reverse light activation
To confirm reverse light activation when reverse gear is engaged
- _Object type: Nominal Test
- _Status: REVIEWED
- _Procedure: 1.Set NIgnitionStatus == Ignition || Activation
  2.Engage gear is in Reverse Gear, GearEngaged == Reverse Gear
- _Pass criteria: NReverseLightStatus = Active && NReverseLampActiveStatus = Active
- _Regression: No
- _Time [hr]: 0.1
- _Test environment: Lab-Car (auto)

## STC-BDY02-1210: Reverse light inactivation
To confirm reverse light inactivation when reverse gear is not engaged
- _Object type: Nominal Test
- _Status: REVIEWED
- _Procedure: 1.Activate Reverse light, (Set NIgnitionStatus == Ignition || Activation
  && GearEngaged == Reverse Gear)
  2.GearEngaged !== Reverse Gear
- _Pass criteria: NReverseLightStatus = inActive && NReverseLampActiveStatus = inActive
- _Regression: No
- _Time [hr]: 0.1
- _Test environment: Lab-Car (auto)

## STC-BDY02-1206: Reverse Light Short circuit fault
To confirm Reverse Light diagnostic strategy when short circuit fault occurs
- _Object type: Nominal Test
- _Status: REVIEWED
- _Procedure: 1.Creat Reverse Light circuit fault i.e., short circuit fault , NReverseLampActiveStatus = Fault
  2.After fault, make sure the drive feedback curent is out of normal operation thresholds
- _Pass criteria: 1.NReverseLampActiveStatus = Inactive
  2.A DTC shall be raised
  3.NReverseLightClusterMessage = Fault
- _Regression: No
- _Time [hr]: 0.1
- _Test environment: Lab-Car (auto)

## STC-BDY02-1207: Reverse Light open circuit fault
To confirm Reverse Light diagnostic strategy when open circuit fault occurs
- _Object type: Nominal Test
- _Status: REVIEWED
- _Procedure: 1.Creat Reverse Light circuit fault i.e., open circuit fault , NReverseLampActiveStatus = Fault
  2.After fault, make sure the drive feedback curent is out of normal operation thresholds
- _Pass criteria: 1.NReverseLampActiveStatus = Inactive
  2.A DTC shall be raised
  3.NReverseLightClusterMessage = Fault
- _Regression: No
- _Time [hr]: 0.1
- _Test environment: Lab-Car (auto)

## STC-BDY02-1208: Reverse Light circuit circuit fault reset
To confirm Reverse Light fault reset with new ignition cycle
- _Object type: Nominal Test
- _Status: REVIEWED
- _Procedure: 1.Creat Reverse Light circuit fault i.e., Open circuit fault, NReverseLampActiveStatus = Fault
  2.After fault, make sure the drive feedback curent is out of normal operation thresholds
  3.Start new ignition cycle
- _Pass criteria: NReverseLampActiveStatus = Inactive
- _Regression: No
- _Time [hr]: 0.1
- _Test environment: Lab-Car (auto)

## STC-BDY02-361: Parking light deactivation
Parking light deactivation when igniton state>2
- _Object type: Negative Test
- _Status: REVIEWED
- _Procedure: 1.Enable parking light function(Ignition status = 2 && NDISwitch=3||1)
  2.Set ignition status > 2
- _Pass criteria: 1.ParkingLightActive = True,
  Side lights, Side Marker and Tail lamps shall active when parking ligts are activated
  2.ParkingLightAvailable = False,
  Side lights, Side Marker and Tail lamps are OFF
- _Regression: No
- _Time [hr]: 0.1
- _Test environment: Lab-Car (auto)

## STC-BDY02-366: Parking light deactivation
Parking light deactivation with direction indicator stalk
- _Object type: Negative Test
- _Status: REVIEWED
- _Procedure: 1.Enable parking light function(Ignition status = 2 && NDISwitch=3||1)
  2.Set NDISwitch! = 3||1
- _Pass criteria: 1.ParkingLightActive = True,
  Side lights, Side Marker and Tail lamps shall active when parking ligts are activated
  2.ParkingLightAvailable = False,
  Side lights, Side Marker and Tail lamps are OFF
- _Regression: No
- _Time [hr]: 0.1
- _Test environment: Lab-Car (auto)

## STC-BDY02-371: Parking light deactivation
Parking light deactivation when battery is very low SOC
- _Object type: Negative Test
- _Status: REVIEWED
- _Procedure: 1.Enable parking light function(Ignition status = 2 && NDISwitch=3||1)
  2.Set INBatteryLowStateOfCharge = 1||2
- _Pass criteria: 1.ParkingLightActive = True,
  Side lights, Side Marker and Tail lamps shall active when parking ligts are activated
  2.ParkingLightAvailable = False,
  Side lights, Side Marker and Tail lamps are OFF
- _Regression: No
- _Time [hr]: 0.1
- _Test environment: Lab-Car (auto)

## STC-BDY02-367: Parking light function NOT available
Parking light function NOT available when ignition state>2
- _Object type: Nominal Test
- _Status: REVIEWED
- _Procedure: 1.Set ignition status > 2
  2.Set direction Indicator stalk in either left or right position (NDISwitch=3||1)
- _Pass criteria: ParkingLightAvailable = False,
  Side lights, Side Marker and Tail lamps shall remain OFF
- _Regression: No
- _Time [hr]: 0.1
- _Test environment: Lab-Car (auto)

## STC-BDY02-362: Parking light activation
- _Object type: Nominal Test
- _Status: REVIEWED
- _Procedure: 1.Set ignition status = 2
  2.Set direction Indicator stalk in either left or right position (NDISwitch=3||1)
- _Pass criteria: ParkingLightActive = True,
  Side lights, Side Marker and Tail lamps shall active when parking ligts are activated
- _Regression: Yes
- _Time [hr]: 0.1
- _Test environment: Lab-Car (auto)

## STC-BDY02-368: Parking light function NOT available
Parking light function NOT available with direction indicator stalk
- _Object type: Nominal Test
- _Status: REVIEWED
- _Procedure: 1.Set ignition status = 2
  2.Set NDISwitch!=3||1
- _Pass criteria: ParkingLightAvailable = False,
  Side lights, Side Marker and Tail lamps shall remain OFF
- _Regression: No
- _Time [hr]: 0.1
- _Test environment: Lab-Car (auto)

## STC-BDY02-369: Parking light function NOT available
Parking light function NOT available with low SOC
- _Object type: Nominal Test
- _Status: REVIEWED
- _Procedure: 1.Set NIgnitionStatus = Awake || Accessory
  2. Set NBatteryLowStateOfCharge != OK
  3.Set NDISwitch=3||1
- _Pass criteria: ParkingLightAvailable = False,
  Side lights, Side Marker and Tail lamps shall remain OFF
- _Regression: No
- _Time [hr]: 0.1
- _Test environment: Lab-Car (auto)

## STC-BDY02-513: Parking Light Left Active
Parking Light Left Activation
- _Object type: Nominal Test
- _Status: REVIEWED
- _Procedure: 1.Set NIgnitionStatus =2
  2. Parking Light Function Available && NDISwitch == Downwards
- _Pass criteria: NSideLightLeftStatus = Active
  NTailLightLeftStatus = Active
  BParkingLightStatus = Active
- _Regression: Yes
- _Time [hr]: 0.2
- _Test environment: Lab-Car (auto)

## STC-BDY02-532: Parking Light Left deActive with ignition state
Parking Light Left deActivation when existing current ignition state
- _Object type: Nominal Test
- _Status: REVIEWED
- _Procedure: 1.Set NIgnitionStatus =2 && Parking lights Inactive
  2.Operate Direction Indicator stalk to Left position, NDISwitch = 1 ( Rising edge)
  3.Set NIgnitionStatus > 2
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Left front Side Lamp, left Side Markers and left rear Tail Lamp shall be deactivated.
  ParkingLightLeftActive= False,
  NSideLStatus=0x0,
  NSidemarkerLeftStatus= 0x0,
  NTailLightLStatus= 0x0,
  NParkingLightsStaus = 0x00( both OFF)
- _Regression: No
- _Time [hr]: 0.2
- _Test environment: Lab-Car (auto)

## STC-BDY02-534: Parking Light Left deActive with low battery value
Parking Light Left deActivation with low battery voltage
- _Object type: Nominal Test
- _Status: REVIEWED
- _Procedure: 1.Set NIgnitionStatus =2 && Parking lights Inactive
  2.Operate Direction Indicator stalk to Left position, NDISwitch = 1 ( Rising edge)
  3.Set NBatteryUVP = 1||2
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Left front Side Lamp, left Side Markers and left rear Tail Lamp shall be deactivated.
  ParkingLightLeftActive= False,
  NSideLStatus=0x0,
  NSidemarkerLeftStatus= 0x0,
  NTailLightLStatus= 0x0,
  NParkingLightsStaus = 0x00( both OFF)
- _Regression: No
- _Time [hr]: 0.2
- _Test environment: Lab-Car (auto)

## STC-BDY02-518: Parking Light Right Active
Parking Light Right Activation
- _Object type: Nominal Test
- _Status: REVIEWED
- _Procedure: 1.Set NIgnitionStatus =2 && Parking lights Inactive
  2.Operate Direction Indicator stalk to Right position, NDISwitch = 3 ( Rising edge)
- _Pass criteria: Right front Side Lamp, Right Side Markers and Right rear Tail Lamp shall be activated.
  ParkingLightRightActive= True,
  NSideRStatus=0x1,
  NSidemarkerRightStatus= 0x1,
  NTailLightLStatus= 0x1,
  NParkingLightsStaus = 0x02( right on)
- _Regression: Yes
- _Time [hr]: 0.2
- _Test environment: Lab-Car (auto)

## STC-BDY02-533: Parking Light Right deActive with ignition state
Parking Light Right deActivation when existing current ignition state
- _Object type: Nominal Test
- _Status: REVIEWED
- _Procedure: 1.Set NIgnitionStatus =2 && Parking lights Inactive
  2.Operate Direction Indicator stalk to Right position, NDISwitch = 3 ( Rising edge)
  3.Set NIgnitionStatus > 2
- _Pass criteria: 2.Right front Side Lamp, Right Side Markers and Right rear Tail Lamp shall be activated.
  ParkingLightRightActive= True,
  NSideRStatus=0x1,
  NSidemarkerRightStatus= 0x1,
  NTailLightLStatus= 0x1,
  NParkingLightsStaus = 0x02( right on)
  3.Right front Side Lamp, Right Side Markers and Right rear Tail Lamp shall be deactivated.
  ParkingLightRightActive= False,
  NSideRStatus=0x0,
  NSidemarkerRightStatus= 0x0,
  NTailLightLStatus= 0x0,
  NParkingLightsStaus = 0x00( both OFF)
- _Regression: No
- _Time [hr]: 0.2
- _Test environment: Lab-Car (auto)

## STC-BDY02-535: Parking Light Right deActive with low battery value
Parking Light Right deActivation with low battery voltage
- _Object type: Nominal Test
- _Status: REVIEWED
- _Procedure: 1.Set NIgnitionStatus =2 && Parking lights Inactive
  2.Operate Direction Indicator stalk to Right position, NDISwitch = 3 ( Rising edge)
  3.Set NBatteryUVP = 1||2
- _Pass criteria: 2.Right front Side Lamp, Right Side Markers and Right rear Tail Lamp shall be activated.
  ParkingLightRightActive= True,
  NSideRStatus=0x1,
  NSidemarkerRightStatus= 0x1,
  NTailLightLStatus= 0x1,
  NParkingLightsStaus = 0x02( right on)
  3.Right front Side Lamp, Right Side Markers and Right rear Tail Lamp shall be deactivated.
  ParkingLightRightActive= False,
  NSideRStatus=0x0,
  NSidemarkerRightStatus= 0x0,
  NTailLightLStatus= 0x0,
  NParkingLightsStaus = 0x00( both OFF)
- _Regression: No
- _Time [hr]: 0.2
- _Test environment: Lab-Car (auto)

## STC-BDY02-514: Left & Right Parking Lights active
Both Left & Right Parking Lights activation
- _Object type: Nominal Test
- _Status: REVIEWED
- _Procedure: 1.Set NIgnitionStatus =2 && Parking lights Inactive
  2.Operate Direction Indicator Stalk in both directions just once i.e.,
  NDISwitch = 1 ( Rising edge) &&
  NDISwitch = 3 (Rising edge)
- _Pass criteria: Both left and right parking lights shall be activated.
  ParkingLightBothActive= True,
  NSideLStatus=0x1,
  NSidemarkerLeftStatus= 0x1,
  NTailLightLStatus= 0x1,
  NSideRStatus=0x1,
  NSidemarkerRightStatus= 0x1,
  NTailLightLStatus= 0x1,
  NParkingLightsStaus = 0x03( both on)
- _Regression: Yes
- _Time [hr]: 0.4
- _Test environment: Lab-Car (auto)

## STC-BDY02-536: Left & Right Parking Lights deactive with ignition state
Both Left & Right Parking Lights deactivation while exiting current ignition state
- _Object type: Nominal Test
- _Status: REVIEWED
- _Procedure: 1.Set NIgnitionStatus =2 && Parking lights Inactive
  2.Operate Direction Indicator Stalk in both directions just once i.e.,
  NDISwitch = 1 ( Rising edge) &&
  NDISwitch = 3 (Rising edge)
  3.Set NIgnitionStatus > 2
- _Pass criteria: 2.Both left and right parking lights shall be activated.
  ParkingLightBothActive= True,
  NSideLStatus=0x1,
  NSidemarkerLeftStatus= 0x1,
  NTailLightLStatus= 0x1,
  NSideRStatus=0x1,
  NSidemarkerRightStatus= 0x1,
  NTailLightLStatus= 0x1,
  NParkingLightsStaus = 0x03( both on)
  3.Both left and right parking lights shall be deactivated.
  ParkingLightBothActive= False,
  NSideLStatus=0x0,
  NSidemarkerLeftStatus= 0x0,
  NTailLightLStatus= 0x0,
  NSideRStatus=0x0,
  NSidemarkerRightStatus= 0x0,
  NTailLightLStatus= 0x0,
  NParkingLightsStaus = 0x00( both OFF)
- _Regression: No
- _Time [hr]: 0.4
- _Test environment: Lab-Car (auto)

## STC-BDY02-537: Left & Right Parking Lights deactive with low battery value
Both Left & Right Parking Lights deactivation with low battery voltage
- _Object type: Nominal Test
- _Status: REVIEWED
- _Procedure: 1.Set NIgnitionStatus =2 && Parking lights Inactive
  2.Operate Direction Indicator Stalk in both directions just once i.e.,
  NDISwitch = 1 ( Rising edge) &&
  NDISwitch = 3 (Rising edge)
  3.Set NBatteryUVP = 1||2
- _Pass criteria: 2.Both left and right parking lights shall be activated.
  ParkingLightBothActive= True,
  NSideLStatus=0x1,
  NSidemarkerLeftStatus= 0x1,
  NTailLightLStatus= 0x1,
  NSideRStatus=0x1,
  NSidemarkerRightStatus= 0x1,
  NTailLightLStatus= 0x1,
  NParkingLightsStaus = 0x03( both on)
  3.Both left and right parking lights shall be deactivated.
  ParkingLightBothActive= False,
  NSideLStatus=0x0,
  NSidemarkerLeftStatus= 0x0,
  NTailLightLStatus= 0x0,
  NSideRStatus=0x0,
  NSidemarkerRightStatus= 0x0,
  NTailLightLStatus= 0x0,
  NParkingLightsStaus = 0x00( both OFF)
- _Regression: No
- _Time [hr]: 0.4
- _Test environment: Lab-Car (auto)

## STC-BDY02-519: Parking Light Left deactive
Parking Light Left deactivation
- _Object type: Nominal Test
- _Status: REVIEWED
- _Procedure: 1.Set NIgnitionStatus =2 && Parking lights Inactive
  2.Operate Direction Indicator stalk to Left position, ParkingLightLeftActive= True && NDISwitch = 1 ( Rising edge)
  3.Operate Direction indicator again to same side, NDISwitch = 1 ( Rising edge)
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Parking light on that side(left) shall be deactivated.
  ParkingLightLeftActive= False
  NSideLStatus=0x0,
  NSidemarkerLeftStatus= 0x0,
  NTailLightLStatus= 0x0
- _Regression: Yes
- _Time [hr]: 0.2
- _Test environment: Lab-Car (auto)

## STC-BDY02-520: Parking Light Right deactive
Parking Light Right deactivation
- _Object type: Nominal Test
- _Status: REVIEWED
- _Procedure: 1.Set NIgnitionStatus =2 && Parking lights Inactive
  2.Operate Direction Indicator stalk to Right position, ParkingLightRightActive= True && NDISwitch = 3 ( Rising edge)
  3.Operate Direction indicator again to same side, NDISwitch = 3 ( Rising edge)
- _Pass criteria: 2.Right front Side Lamp, Right Side Markers and Right rear Tail Lamp shall be activated.
  ParkingLightRightActive= True,
  NSideRStatus=0x1,
  NSidemarkerRightStatus= 0x1,
  NTailLightRStatus= 0x1,
  NParkingLightsStaus = 0x02( Right on)
  3.Parking light on that side(Right ) shall be deactivated.
  ParkingLightRight Active= False
  NSideRStatus=0x0,
  NSidemarkerRightStatus= 0x0,
  NTailLightRStatus= 0x0
- _Regression: Yes
- _Time [hr]: 0.2
- _Test environment: Lab-Car (auto)

## STC-BDY02-523: Left parking light activation with Right light already in active state
Left Parking Light activation while Right light was in active state
- _Object type: Nominal Test
- _Status: REVIEWED
- _Procedure: 1.Set NIgnitionStatus =2 && Parking lights Inactive
  2.Operate Direction indicator to Right side, NDISwitch = 3 ( Rising edge)
  3.Operate Direction indicator to Left side, NDISwitch = 1 ( Rising edge)
- _Pass criteria: 2.Right front Side Lamp, Right Side Markers and Right rear Tail Lamp shall be activated.
  ParkingLightRightActive= True,
  NSideRStatus=0x1,
  NSidemarkerRightStatus= 0x1,
  NTailLightLStatus= 0x1,
  NParkingLightsStaus = 0x02( right on)
  3.Both left and right parking lights shall be activated.
  ParkingLightBothActive= True,
  NSideLStatus=0x1,
  NSidemarkerLeftStatus= 0x1,
  NTailLightLStatus= 0x1,
  NSideRStatus=0x1,
  NSidemarkerRightStatus= 0x1,
  NTailLightRStatus= 0x1,
  NParkingLightsStaus = 0x03( both on)
- _Regression: No
- _Time [hr]: 0.2
- _Test environment: Lab-Car (auto)

## STC-BDY02-524: Right parking light activation with Left light already in active state
Right Parking Light activation while Left light was in active state
- _Object type: Nominal Test
- _Status: REVIEWED
- _Procedure: 1.Set NIgnitionStatus =2 && Parking lights Inactive
  2.Operate Direction indicator to Left side, NDISwitch = 1 ( Rising edge)
  3.Operate Direction indicator to Right side, NDISwitch = 3 ( Rising edge)
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Both left and right parking lights shall be activated.
  ParkingLightBothActive= True,
  NSideLStatus=0x1,
  NSidemarkerLeftStatus= 0x1,
  NTailLightLStatus= 0x1,
  NSideRStatus=0x1,
  NSidemarkerRightStatus= 0x1,
  NTailLightRStatus= 0x1,
  NParkingLightsStaus = 0x03( both on)
- _Regression: No
- _Time [hr]: 0.2
- _Test environment: Lab-Car (auto)

## STC-BDY02-525: Both Parking Lights deactive
Both Left & Right Parking Lights (Right followed by Left)deactivation when both parking lights are active
- _Object type: Nominal Test
- _Status: REVIEWED
- _Procedure: 1.Set NIgnitionStatus =2 && Parking lights Inactive
  2.Operate Direction Indicator Stalk in both directions just once i.e.,
  NDISwitch = 1 ( Rising edge) &&
  NDISwitch = 3 (Rising edge)
  3.Operate Direction indicator to Left side, NDISwitch = 1 ( Rising edge)
  4.Operate Direction indicator to Right side, NDISwitch = 3 ( Rising edge)
- _Pass criteria: 2.Both left and right parking lights shall be activated.
  ParkingLightBothActive= True,
  NSideLStatus=0x1,
  NSidemarkerLeftStatus= 0x1,
  NTailLightLStatus= 0x1,
  NSideRStatus=0x1,
  NSidemarkerRightStatus= 0x1,
  NTailLightRStatus= 0x1,
  NParkingLightsStaus = 0x03( both on)
  3.Parking light on that side(left) shall be deactivated and Right side shall be in active state.
  ParkingLightLeftActive= False
  NSideLStatus=0x0,
  NSidemarkerLeftStatus= 0x0,
  NTailLightLStatus= 0x0,
  NSideRStatus=0x1,
  NSidemarkerRightStatus= 0x1,
  NTailLightRStatus= 0x1,
  NParkingLightsStaus = 0x02( Right on)
  4.Both left and right parking lights shall be deactivated.
  ParkingLightBothActive= False,
  NSideLStatus=0x0,
  NSidemarkerLeftStatus= 0x0,
  NTailLightLStatus= 0x0,
  NSideRStatus=0x0,
  NSidemarkerRightStatus= 0x0,
  NTailLightRStatus= 0x0,
  NParkingLightsStaus = 0x00( both OFF)
- _Regression: No
- _Time [hr]: 0.2
- _Test environment: Lab-Car (auto)

## STC-BDY02-527: Left Parking light telltale
Left Parking Light status to DriverDisplay
- _Object type: Nominal Test
- _Status: REVIEWED
- _Procedure: Activate Left Parking light:
  Set NIgnitionStatus =2 && NDISwitch = 1 ( Rising edge)
- _Pass criteria: Status of the Left Parking Light shall be communicated to the cluster
- _Regression: Yes
- _Time [hr]: 0.2
- _Test environment: Lab-Car (manual)

## STC-BDY02-528: Right Parking light telltale
Right Parking Light status to DriverDisplay
- _Object type: Nominal Test
- _Status: REVIEWED
- _Procedure: Activate Right Parking light:
  Set NIgnitionStatus =2 && NDISwitch = 3 ( Rising edge)
- _Pass criteria: Status of the Right Parking Light shall be communicated to the cluster
- _Regression: Yes
- _Time [hr]: 0.2
- _Test environment: Lab-Car (manual)

## STC-BDY02-515: Parking lights telltale
Left & Right Parking Lights status to DriverDisplay
- _Object type: Nominal Test
- _Status: REVIEWED
- _Procedure: Activate Left & Right Parking light:
  Set NIgnitionStatus =2 && NDISwitch = 1 ( Rising edge) && NDISwitch = 3 ( Rising edge)
- _Pass criteria: Status of the both Left & Right Parking Lights shall be communicated to the cluster
- _Regression: Yes
- _Time [hr]: 0.2
- _Test environment: Lab-Car (manual)

## STC-BDY02-529: DCU awake with Left parking light
DCU shall stay awake in ignition 0,1 while Left parking light is active
- _Object type: Nominal Test
- _Status: REVIEWED
- _Procedure: 1.Activate Left Parking light:
  Set NIgnitionStatus =2 && NDISwitch = 1 ( Rising edge)
  2.Deactive Left Parking light:NDISwitch = 1 ( Rising edge)
- _Pass criteria:
  1. DCU shall stay awake in Ignition 0,1 until left parking light is active
  2.DCU shall no longer be awake
- _Regression: No
- _Time [hr]: 0.2
- _Test environment: Lab-Car (manual)

## STC-BDY02-530: DCU awake with Right parking light
DCU shall stay awake in ignition 0,1 while Right parking light is active
- _Object type: Nominal Test
- _Status: REVIEWED
- _Procedure: 1.Activate Right Parking light:
  Set NIgnitionStatus =2 && NDISwitch = 3 ( Rising edge)
  2.Deactive Right Parking light:NDISwitch = 3 ( Rising edge)
- _Pass criteria:
  1. DCU shall stay awake in Ignition 0,1 until Right parking light is active
  2.DCU shall no longer be awake
- _Regression: No
- _Time [hr]: 0.2
- _Test environment: Lab-Car (manual)

## STC-BDY02-531: DCU awake with parking lights
DCU shall stay awake in ignition 0,1 while parking lights are active
- _Object type: Nominal Test
- _Status: REVIEWED
- _Procedure: 1.Activate Parking lights:
  Set NIgnitionStatus =2 && NDISwitch = 1 ( Rising edge) && NDISwitch = 3 ( Rising edge)
  2.Deactive Left Parking light: NDISwitch = 1 ( Rising edge)
  3.Deactive Right Parking light: NDISwitch = 3 ( Rising edge)
- _Pass criteria:
  1. DCU shall stay awake in Ignition 0,1 until any of the parking light is active
  2.DCU shall stay awake in Ignition 0,1 until any of the parking light is active
  3.DCU shall no longer be awake
- _Regression: No
- _Time [hr]: 0.2
- _Test environment: Lab-Car (manual)

## STC-BDY02-238: LH brake/Tail lamp output - S/C(GND)
DTC B122211 for LH brake/Tail lamp output is short to ground
- _Object type: Fault Test
- _Status: REVIEWED
- _Procedure: 1.Set ignition state to 1
  2.Short LH brake/Tail lamp output pin(xx) to ground(xx) for a duration of fault calibratable debounce period
  3.Remove the short b/w ouput pin to ground after fault calibratable debounce period
  4.Repeat steps 2,3 for all the ignition states
- _Pass criteria: 2.DTC B122211 shall be logged in current state in ZC1.
  Check cluster message CAN value.
  3.DTC B122211 shall be in healed state in ZC1.
  No cluster message CAN value.
- _Regression: No
- _Time [hr]: 0.4
- _Test environment: Lab-Car (auto)

## STC-BDY02-239: RH brake/Tail lamp output - S/C(GND)
DTC B12111 RH brake/Tail lamp output is short to ground
- _Object type: Fault Test
- _Status: REVIEWED
- _Procedure: 1.Set ignition state to 1
  2.Short RH brake/Tail lamp output pin(xx) to ground(xx) for a duration of fault calibratable debounce period
  3.Remove the short b/w ouput pin to ground after fault calibratable debounce period
  4.Repeat steps 2,3 for all the ignition states
- _Pass criteria: 2.DTC B12111 shall be logged in current state in ZC1.
  Check cluster message CAN value.
  3.DTC B12111 shall be in healed state in ZC1.
  No cluster message CAN value.
- _Regression: No
- _Time [hr]: 0.4
- _Test environment: Lab-Car (auto)

## STC-BDY02-240: Master light switch - voltage out of range
DTC B12011C Master light switch output voltage is out of range
- _Object type: Fault Test
- _Status: REVIEWED
- _Procedure: 1.Set ignition state to 1
  2.Short the master light switch output pin(xx) to battery voltage pin(xx) or open the output pin(xx) for a duration of fault calibratable debounce period
  3.Remove the short b/w ouput pin to battery after fault calibratable debounce period
  4.Repeat steps 2,3 for all the ignition states
- _Pass criteria: 2.DTC B12011Cshall be logged in current state in ZC1.
  Check cluster message CAN value.
  3.DTC B12011C shall be in healed state in ZC1.
  No cluster message CAN value.
- _Regression: No
- _Time [hr]: 0.4
- _Test environment: Lab-Car (auto)

## STC-BDY02-241: LH LED headlamp - S/C(GND)
DTC B122011 LH LED headlamp output short circuit to ground
- _Object type: Fault Test
- _Status: REVIEWED
- _Procedure: 1.Set ignition state to 1
  2.Short left hand headlamp output pin(xx) to ground(xx) for a duration of fault calibratable debounce period
  3.Remove the short b/w ouput pin to ground after fault calibratable debounce period
  4.Repeat steps 2,3 for all the ignition states
- _Pass criteria: 2.DTC B122011 shall be logged in current state in ZA1.
  Check cluster message CAN value.
  3.DTC B122011 shall be in healed state in ZA1.
  No cluster message CAN value.
- _Regression: No
- _Time [hr]: 0.4
- _Test environment: Lab-Car (auto)

## STC-BDY02-243: RH LED headlamp - S/C(GND)
DTC B121F11 RH LED headlamp output short circuit to ground
- _Object type: Fault Test
- _Status: REVIEWED
- _Procedure: 1.Set ignition state to 1
  2.Short right hand headlamp output pin(xx) to ground(xx) for a duration of fault calibratable debounce period
  3.Remove the short b/w ouput pin to ground after fault calibratable debounce period
  4.Repeat steps 2,3 for all the ignition states
- _Pass criteria: 2.DTC B121F11 shall be logged in current state in ZA1.
  Check cluster message CAN value.
  3.DTC B121F11 shall be in healed state in ZA1.
  No cluster message CAN value.
- _Regression: No
- _Time [hr]: 0.4
- _Test environment: Lab-Car (auto)

## STC-BDY02-468: Left lamp -shrt to GND
Main beam headlamp output left side-short to ground
- _Object type: Fault Test
- _Status: REVIEWED
- _Procedure: 1.Set ignition state to 1
  2.Short the main beam headlamp left side output pin(xx) to ground pin(xx) for a duration of fault calibratable debounce period
  3.Remove the short b/w ouput pin to ground after fault calibratable debounce period
  4.Repeat steps 2,3 for all other ignition states
- _Pass criteria: 2.DTC XXX shall be logged in current state in ZA1.
  Check for cluster message CAN value.
  3.DTC XXX shall be in healed state in ZA1.
  No cluster message CAN value.
- _Regression: No
- _Time [hr]: 0.5
- _Test environment: Lab-Car (auto)

## STC-BDY02-469: Left lamp -shrt to BATT or Open ckt
Main beam headlamp output left side-short to battery or open circuit
- _Object type: Fault Test
- _Status: REVIEWED
- _Procedure: 1.Set ignition state to 1
  2.Short the main beam headlamp left side output pin(xx) to battery voltage pin(xx) or open the output pin(xx) for a duration of fault calibratable debounce period
  3.Remove the short b/w ouput pin to battery after fault calibratable debounce period
  4.Repeat steps 2,3 for all other ignition states
- _Pass criteria: 2.DTC XXX shall be logged in current state in ZA1.
  Check cluster message CAN value.
  3.DTC XXX shall be in healed state in ZA1.
  No cluster message CAN value.
- _Regression: No
- _Time [hr]: 0.5
- _Test environment: Lab-Car (auto)

## STC-BDY02-470: Right lamp -shrt to GND
Main beam headlamp output right side-short to ground
- _Object type: Fault Test
- _Status: REVIEWED
- _Procedure: 1.Set ignition state to 1
  2.Short the main beam headlamp right side output pin(xx) to ground pin(xx) for a duration of fault calibratable debounce period
  3.Remove the short b/w ouput pin to ground after fault calibratable debounce period
  4.Repeat steps 2,3 for all other ignition states
- _Pass criteria: 2.DTC XXX shall be logged in current state in ZA1.
  Check cluster message CAN value.
  3.DTC XXX shall be in healed state in ZA1.
  No cluster message CAN value.
- _Regression: No
- _Time [hr]: 0.5
- _Test environment: Lab-Car (auto)

## STC-BDY02-471: Right lamp -shrt to BATT or Open ckt
Main beam headlamp output rught side-short to battery or open circuit
- _Object type: Fault Test
- _Status: REVIEWED
- _Procedure: 1.Set ignition state to 1
  2.Short the main beam headlamp right side output pin(xx) to battery voltage pin(xx) or open the output pin(xx) for a duration of fault calibratable debounce period
  3.Remove the short b/w ouput pin to battery after fault calibratable debounce period
  4.Repeat steps 2,3 for all other ignition states
- _Pass criteria: 2.DTC XXX shall be logged in current state in ZA1.
  Check for cluster message CAN value.
  3.DTC XXX shall be in healed state in ZA1.
  No cluster message CAN value.
- _Regression: No
- _Time [hr]: 0.5
- _Test environment: Lab-Car (auto)

## STC-BDY02-1368: SW Composition ExteriorLightingSafetyZa1
Composition Check
- _Object type: Misuse Test
- _Status: REVIEWED
- _Procedure: The SW composition ExteriorLightingSafetyZa1 implementing the safety monitoring of this function is designed.
- _Pass criteria: Verify that the SW composition is the only connected to the actuations of the outputs.
- _Regression: No
- _Time [hr]: 0.1
- _Test environment: HIL (manual)

## STC-BDY02-1503: SW Composition Master Light Control
Composition Check
- _Object type: Misuse Test
- _Status: REVIEWED
- _Procedure: The SW composition Master Light Control is defined.
- _Pass criteria: Verify that the compositions Master Light Control is not connected to any actuation of the outputs.
- _Regression: No
- _Time [hr]: 0.1
- _Test environment: HIL (manual)

## STC-BDY02-1369: High Side Command Headlamp
The ExteriorLightingSafetyZa1 command :
Headlamp_Ctrl_PWR_RH (HSD11_2)
Headlamp_Ctrl_PWR_LH (HSD11_1)
Headlamp_Relay_2_Ctrl (HB5A)
as requested by:
BLH_DippedBeamActivate_Req AND
BRH_DippedBeamActivate_Req during all times
- _Object type: Misuse Test
- _Status: REVIEWED
- _Procedure: Test Steps :
  BLH_DippedBeamActivate_Req
  BRH_DippedBeamActivate_Req
  during all NIgnitionStatus 0x05 when moniroting is not active
- _Pass criteria: Verify that :
  Headlamp_Ctrl_PWR_RH (HSD11_2)
  Headlamp_Ctrl_PWR_LH (HSD11_1
  Headlamp_Relay_2_Ctrl (HB5A)
- _Regression: No
- _Time [hr]: 0.1
- _Test environment: HIL (manual)

## STC-BDY02-1505: Main beam activation
The ExteriorLightingSafetyZa1 shall command
Headlamp_Relay_2_Ctrl (HB5A)
as requested by
BFrontLampPWRSupply_Req during all times
- _Object type: Misuse Test
- _Status: REVIEWED
- _Procedure: Test Steps :
  BFrontLampPWRSupply_Req
  during all NIgnitionStatus 0x05 when moniroting is not active
- _Pass criteria: Verify that :
  Headlamp_Relay_2_Ctrl (HB5A) as commanded
- _Regression: No
- _Time [hr]: 0.1
- _Test environment: Lab-Car (manual)

## STC-BDY02-1370: MasterLightSwitch in Dipped Beam On Status
The ExteriorLightingSafetyZa1 detect when all the below occur:
NMasterLightSwitchStatusFuSa = 0x4 (DIPPED BEAM ON)
BLH_DippedBeamActivate_Req = "no activation request"
BRH_DippedBeamActivate_Req = "no activation request"
NIgnitionStatus ==0x5 (Ignition)
within DTI = 100ms.
- _Object type: Misuse Test
- _Status: REVIEWED
- _Procedure: Test Steps :
  NMasterLightSwitchStatusFuSa = 0x4 (DIPPED BEAM ON) && BLH_DipperBeamActivate_Req = No activation request & BRH_DippedBeamActivate_Req = No activation request &&
  NIgnitionStatus ==0x5
- _Pass criteria: Verify that :
  Headlamp_Ctrl_PWR_RH (HSD11_2) = 100 % duty cycle command &&
  Headlamp_Ctrl_PWR_LH (HSD11_1) = 100% duty cycle && Headlamp_Relay_2_Ctrl (HB5A) = HIgh
- _Regression: No
- _Time [hr]: 0.1
- _Test environment: HIL (manual)

## STC-BDY02-1506: MasterLightSwitchFault in Active Status
The ExteriorLightingSafetyZa1 shall detect when all the below occur:
BMasterLightSwitchFaultStatusFuSa = Active
BLH_DippedBeamActivate_Req = "no activation request"
BRH_DippedBeamActivate_Req = "no activation request"
NIgnitionStatus ==0x5 (Ignition)
within DTI = 100ms.
- _Object type: Misuse Test
- _Status: REVIEWED
- _Procedure: Test Steps :
  BMasterLightSwitchFaultStatusFuSa = Active && BLH_DipperBeamActivate_Req = No activation request & BRH_DippedBeamActivate_Req = No activation request &&
  NIgnitionStatus ==0x5
- _Pass criteria: Verify that :
  Headlamp_Ctrl_PWR_RH (HSD11_2) = 100 % duty cycle command &&
  Headlamp_Ctrl_PWR_LH (HSD11_1) = 100% duty cycle
  Headlamp_Relay_2_Ctrl (HB5A) = HIgh
- _Regression: No
- _Time [hr]: 0.1
- _Test environment: HIL (manual)

## STC-BDY02-1507: Safe State #BDY02_FL_1
Upon detection of [STC-BDY02-1370] or [STC-BDY02-1506] the ExteriorLightingSafetyZa1 transition to Safe State #BDY02_FL_1.
- _Object type: Misuse Test
- _Status: REVIEWED
- _Procedure: Test Steps :
  NMasterLightSwitchStatusFuSa = 0x4 (DIPPED BEAM ON) && BLH_DipperBeamActivate_Req = No activation request & BRH_DippedBeamActivate_Req = No activation request
- _Pass criteria: Verify that :
  Headlamp_Ctrl_PWR_RH (HSD11_2) = 100 % duty cycle command &&
  Headlamp_Ctrl_PWR_LH (HSD11_1) = 100% duty cycle && Headlamp_Relay_2_Ctrl (HB5A) = HIgh
- _Regression: No
- _Time [hr]: 0.1
- _Test environment: HIL (manual)

## STC-BDY02-1508: Critical temperature threshold
No action is to be taken when DcuMonTemperatureSafetyMaskZa1 = Critical temperature threshold.
- _Object type: Misuse Test
- _Status: REVIEWED
- _Procedure: DcuMonTemperatureSafetyMaskZa1 = Critical temperature threshold.
- _Pass criteria: No reaction.
- _Regression: No
- _Time [hr]: 0.1
- _Test environment: HIL (manual)

## STC-BDY02-1371: High Side Command Headlamp with with max duty
Headlamp duty command
- _Object type: Misuse Test
- _Status: REVIEWED
- _Procedure: The ExteriorLightingSafetyZa1 command 100% duty cycle the outputs:
  Headlamp_Ctrl_PWR_RH (HSD11_2)
  Headlamp_Ctrl_PWR_LH (HSD11_1)
- _Pass criteria: Verify that both Headlamps are lighted on.
- _Regression: No
- _Time [hr]: 0.1
- _Test environment: HIL (manual)

## STC-BDY02-1509: High Side Command Headlamp with with relay
Headlamp relay command
- _Object type: Misuse Test
- _Status: REVIEWED
- _Procedure: The ExteriorLightingSafetyZa1 command "High side activated":
  Headlamp_Relay_2_Ctrl (HB5A)
- _Pass criteria: Verify that both Headlamps are lighted on.
- _Regression: No
- _Time [hr]: 0.1
- _Test environment: HIL (manual)

## STC-BDY02-1510: ElcSafety
ElcSafety command safety signals
- _Object type: Misuse Test
- _Status: REVIEWED
- _Procedure: The ElcSafety command the below signal:
  NFlcSafetyClusterMessage = "fault value"
  FlcSafetyStatusMask = TBD (specific fault detected i.e. short to gound, battery, open, etc.)
- _Pass criteria: Verify that both signal are activated.
- _Regression: No
- _Time [hr]: 0.1
- _Test environment: HIL (manual)

## STC-BDY02-1372: Safe State #BDY02_FL_1 Action
While in Safe State #BDY02_FL_1, the ExteriorLightingSafetyZa1 perform the action specified in [STC-BDY02-1371], [STC-BDY02-1509] within FRT = 100 ms.
- _Object type: Misuse Test
- _Status: REVIEWED
- _Procedure: Test Steps :
  Master Light switch status = Step4 && BLH_DipperBeamActivate_Req = No activation request & BRH_DipperBeamActivate_Req = No activation request
  HW failures (i.e. short to ground, open, short to battery, out of range) on the signal specified in [1334]
- _Pass criteria: Verify that Dipped Beam is activated.
- _Regression: No
- _Time [hr]: 0.1
- _Test environment: HIL (manual)

## STC-BDY02-1511: Safe State #BDY02_FL_1 exit condition
The ExteriorLightingSafetyZa1 exit Safe State #BDY02_FL_1 at the new vehicle ignition cycle or after a healing time interval, HTI= 3 secs, when the fault no longer exists.
- _Object type: Misuse Test
- _Status: REVIEWED
- _Procedure: Next Ignition Cycle OR HTI=3s
- _Pass criteria: Verify that exit Safe State #BDY02_2 and Normal Operation of ElcSafety.
- _Regression: No
- _Time [hr]: 0.1
- _Test environment: HIL (manual)

## STC-BDY02-1374: Safe State #BDY02_FL_2 Action
While in Safe State #BDY02_FL_2 , the ExteriorLightingSafetyZa1 perform the action specified in [STC-BDY02-1510] within FRT = 100 ms.
- _Object type: Misuse Test
- _Status: REVIEWED
- _Procedure: Test Steps :
  HW failures (i.e. short to ground, open, short to battery, out of range) on the signal specified in [1341] OR
  No command to activate Dipped beam
- _Pass criteria: Verify that the warning sent to driver.
- _Regression: No
- _Time [hr]: 0.1
- _Test environment: HIL (manual)

## STC-BDY02-1376: Safe State #BDY02_FL_2 exit condition
The ExteriorLightingSafetyZa1 exit Safe State #BDY02_FL_2 at the new vehicle ignition cycle or after a healing time interval, HTI= 3 secs, when the fault no longer exists.
- _Object type: Misuse Test
- _Status: REVIEWED
- _Procedure: Next Ignition Cycle OR HTI=3s
- _Pass criteria: Verify that exit Safe State #BDY02_3 and Normal Operation of ElcSafety.
- _Regression: No
- _Time [hr]: 0.1
- _Test environment: HIL (manual)

## STC-BDY02-1515: Safe State #BDY02_FL_3 Action
While in Safe State #BDY02_FL_3 , the ExteriorLightingSafetyZa1 perform the action specified in [STC-BDY02-1510] within FRT = 100 ms.
- _Object type: Misuse Test
- _Status: REVIEWED
- _Procedure: Test Steps :
  HW failures (i.e. short to ground, open, short to battery, out of range) on the signal specified in [1341] OR
  No command to activate Dipped beam
- _Pass criteria: Verify that the warning sent to driver and request of emergency activation to ZB1.
- _Regression: No
- _Time [hr]: 0.1
- _Test environment: HIL (manual)

## STC-BDY02-1517: Safe State #BDY02_FL_3 exit condition
The ExteriorLightingSafetyZa1 exit Safe State #BDY02_FL_3 at the new vehicle ignition cycle or after a healing time interval, HTI= 3 secs, when the fault no longer exists.
- _Object type: Misuse Test
- _Status: REVIEWED
- _Procedure: Next Ignition Cycle OR HTI=3s
- _Pass criteria: Verify that exit Safe State #BDY02_3 and Normal Operation of ElcSafety.
- _Regression: No
- _Time [hr]: 0.1
- _Test environment: HIL (manual)

## STC-BDY02-1381: ExteriorLightingSafetyZa1 signal received
Signal received check
- _Object type: Misuse Test
- _Status: REVIEWED
- _Procedure: The ExteriorLightingSafetyZa1 receive the following signals:
  NMasterLightSwitchStatusFuSa
  BMasterLightSwitchFaultStatusFuSa
  EflcSafetyStatusMask
  BLH_DippedBeamActivate_Req
  BRH_DippedBeamActivate_Req
  Headlamp_PWR_Status_RH (DI2)
  Headlamp_PWR_Status_LH (DI1)
  DcuMonTemperatureSafetyMaskZa1
  NIgnitionStatus
  BFrontLampPWRSupply_Req
- _Pass criteria: Verify that ExteriorLightingSafetyZa1 receive all signals.
  The message containing the signals :
  NMasterLightSwitchStatusFuSa
  BMasterLightSwitchFaultStatusFuSa
  EflcSafetyStatusMask
  NIgnitionStatus
  is protected with E2E.
- _Regression: No
- _Time [hr]: 0.1
- _Test environment: HIL (manual)

## STC-BDY02-1384: No activation command to activate dipped beam on driver request
The ExteriorLightingSafetyZa1 detect the following:
Headlamp_Relay_2_Ctrl (HB5A) is commanded "High side activated"; AND
any of the signal specified in [1336] is read LOW
within DTI = 200ms.
- _Object type: Misuse Test
- _Status: REVIEWED
- _Procedure: No activation command to activate dipped beam on driver request. Either of the signals below is read LOW :
  Headlamp_PWR_Status_RH (DI2)
  Headlamp_PWR_Status_LH (DI1)
- _Pass criteria: Verify that the warning sent to driver.
- _Regression: No
- _Time [hr]: 0.1
- _Test environment: HIL (manual)

## STC-BDY02-1518: Status of head lamp activation command detected
Upon detection of [STC-BDY02-1384], the ExteriorLightingSafetyZa1 transition to Safe State #BDY02_FL_2.
- _Object type: Misuse Test
- _Status: REVIEWED
- _Procedure: Status of head lamp activation command detected LOW :
  Either of the signals below is read LOW :
  Headlamp_PWR_Status_RH (DI2)
  Headlamp_PWR_Status_LH (DI1)
- _Pass criteria: Verify that the warning sent to driver.
- _Regression: No
- _Time [hr]: 0.1
- _Test environment: HIL (manual)

## STC-BDY02-1519: Dipped Beam activation
The ExteriorLightingSafetyZa1 detect a communication error in the signal [1334] within DTI = 200ms.
- _Object type: Misuse Test
- _Status: REVIEWED
- _Procedure: Communication error.
- _Pass criteria: Verify that the Dipped Beam is activated.
  within DTI = 200ms.
- _Regression: No
- _Time [hr]: 0.1
- _Test environment: HIL (manual)

## STC-BDY02-1520: Safe State #BDY02_FL_1
Upon detection of [STC-BDY02-1519], the ExteriorLightingSafetyZa1 transition to Safe State #BDY02_FL_1.
- _Object type: Misuse Test
- _Status: REVIEWED
- _Procedure: Communication error.
- _Pass criteria: Verify that the Dipped Beam is activated.
- _Regression: No
- _Time [hr]: 0.1
- _Test environment: HIL (manual)

## STC-BDY02-1521: Communication error on many signals
The ExteriorLightingSafetyZa1 detect a communication error in the signal NignitionStatus AND NMasterLightSwitchStatusFuSa=0X4 OR BMasterLightSwitchFaultStatusFuSa = Active, within DTI = 200ms.
- _Object type: Misuse Test
- _Status: REVIEWED
- _Procedure: Communication error on NignitionStatus.
- _Pass criteria: Verify that the Dipped Beam is activated.
  within DTI = 200ms.
- _Regression: No
- _Time [hr]: 0.1
- _Test environment: HIL (manual)

## STC-BDY02-1522: Safe State #BDY02_FL_1
Upon detection of [STC-BDY02-1521], the ExteriorLightingSafetyZa1 transition to Safe State #BDY02_FL_1.
- _Object type: Misuse Test
- _Status: REVIEWED
- _Procedure: Communication error on NignitionStatus.
- _Pass criteria: Verify that the Dipped Beam is activated.
- _Regression: No
- _Time [hr]: 0.1
- _Test environment: HIL (manual)

## STC-BDY02-1523: E2E protection 1
Signals Check
- _Object type: Misuse Test
- _Status: REVIEWED
- _Procedure: The ExteriorLightingSafetyZa1 command the following signals:
  Headlamp_Relay_2_Ctrl (HB5A)
  Headlamp_Ctrl_PWR_RH (HSD11_2)
  Headlamp_Ctrl_PWR_LH (HSD11_1)
  FlcSafetyStatusMask
- _Pass criteria: Verify that the message containing the signal specified is protected with an E2E protection mechanism.
- _Regression: No
- _Time [hr]: 0.1
- _Test environment: HIL (manual)

## STC-BDY02-1525: E2E protection 2
Signal Check
- _Object type: Misuse Test
- _Status: REVIEWED
- _Procedure: The ExteriorLightingSafetyZa1 output a 32-bits signal called FlcSafetyStatusMask to communicate to the Elc (QM SWC) and ExteriorLightingSafetyZb1 the faults status.
- _Pass criteria: Verify that the message containing the signal specified is protected with an E2E protection mechanism.
- _Regression: No
- _Time [hr]: 0.1
- _Test environment: HIL (manual)

## STC-BDY02-1524: HW failures on Headlamp_Relay_2_Ctrl
The ExteriorLightingSafetyZa1 detect HW failures (i.e. short to ground, open, short to battery, out of range) on the signal Headlamp_Relay_2_Ctrl (HB5A) within DTI = 200ms.
- _Object type: Misuse Test
- _Status: REVIEWED
- _Procedure: HW fault on :
  Headlamp_Relay_2_Ctrl (HB5A)
- _Pass criteria: Verify that the warning sent to driver
  ZB1 activate the front light only in case of open circuit.
- _Regression: No
- _Time [hr]: 0.1
- _Test environment: HIL (manual)

## STC-BDY02-1526: Safe State #BDY02_FL_3
Upon detection of [STC-BDY02-1524], the ExteriorLightingSafetyZa1 transition to Safe State #BDY02_FL_3.
- _Object type: Misuse Test
- _Status: REVIEWED
- _Procedure: HW fault on :
  Headlamp_Relay_2_Ctrl (HB5A)
- _Pass criteria: Verify that the warning sent to driver
  ZB1 activate the front light only in case of open circuit.
- _Regression: No
- _Time [hr]: 0.1
- _Test environment: HIL (manual)

## STC-BDY02-1527: HW failures on Headlamp_Ctrl_PWR_RH and Headlamp_Ctrl_PWR_LH
The ExteriorLightingSafetyZa1 detect HW failures (i.e. short to ground, open, short to battery, out of range) on the signals Headlamp_Ctrl_PWR_RH (HSD11_2) and
Headlamp_Ctrl_PWR_LH (HSD11_1) within DTI = 200ms.
- _Object type: Misuse Test
- _Status: REVIEWED
- _Procedure: HW fault on :
  Headlamp_Ctrl_PWR_RH (HSD11_2
  Headlamp_Ctrl_PWR_LH (HSD11_1)
- _Pass criteria: Verify that the warning sent to driver.
- _Regression: No
- _Time [hr]: 0.1
- _Test environment: HIL (manual)

## STC-BDY02-1528: Safe State #BDY02_FL_2
Upon detection of [STC-BDY02-1527], the ExteriorLightingSafetyZa1 shall transition to Safe State #BDY02_FL_2.
- _Object type: Misuse Test
- _Status: REVIEWED
- _Procedure: HW fault on :
  Headlamp_Ctrl_PWR_RH (HSD11_2
  Headlamp_Ctrl_PWR_LH (HSD11_1)
- _Pass criteria: Verify that the warning sent to driver.
- _Regression: No
- _Time [hr]: 0.1
- _Test environment: HIL (manual)

## STC-BDY02-1387: SW Composition ExteriorLightingSafetyZb2
Composition Check
- _Object type: Misuse Test
- _Status: REVIEWED
- _Procedure: The SW composition ExteriorLightingSafetyZb2 implementing the safety monitoring of this function is designed.
- _Pass criteria: Verify that the SW composition is connected to the actuations of the outputs.
- _Regression: No
- _Time [hr]: 0.1
- _Test environment: HIL (manual)

## STC-BDY02-1390: FlcSafetyStatusMask in fault
Command Check
- _Object type: Misuse Test
- _Status: REVIEWED
- _Procedure: When the signal FlcSafetyStatusMask == "open circuit fault"
- _Pass criteria: The ExteriorLightingSafetyZb1 command:
  Headlamp_Relay_2_Ctrl2 (HSD9_1) = "High side activated"
  EflcSafetyStatusMask = bit 1
- _Regression: No
- _Time [hr]: 0.1
- _Test environment: HIL (manual)

## STC-BDY02-1530: NMasterLightSwitchStatusFuSa value
Master Light Switch Resistor Ladder 1 Voltage
- _Object type: Misuse Test
- _Status: REVIEWED
- _Procedure: The ExteriorLightingSafetyZb1 set the signal NMasterLightSwitchStatusFuSa values accordingly with the voltage of the input signal Master Light Switch Resistor Ladder 1 (AN14_PI2).
- _Pass criteria: Verify that the voltage is as for table [1394] and check NMasterLightSwitchStatus.
- _Regression: No
- _Time [hr]: 0.1
- _Test environment: HIL (manual)

## STC-BDY02-1573: Critical temperature threshold
No action is to be taken when DcuMonTemperatureSafetyMaskZb1 = Critical temperature threshold.
- _Object type: Misuse Test
- _Status: REVIEWED
- _Procedure: DcuMonTemperatureSafetyMaskZb1 = Critical temperature threshold
- _Pass criteria: No reaction
- _Regression: No
- _Time [hr]: 0.1
- _Test environment: HIL (manual)

## STC-BDY02-1531: Input Interfaces
Signal Check
- _Object type: Misuse Test
- _Status: REVIEWED
- _Procedure: The ExteriorLightingSafetyZb1 receive the following signals from the ExteriorLightingSafetyZa1:
  FlcSafetyStatusMask
- _Pass criteria: Make Sure ExteriorLightingSafetyZb1 is receiving following signals
  FlcSafetyStatusMask
  Verify that the message containing the signal is protected with appropriate E2E mechanism.
- _Regression: No
- _Time [hr]: 0.1
- _Test environment: Lab-Car (manual)

## STC-BDY02-1533: Input Interfaces
Signals Check
- _Object type: Misuse Test
- _Status: REVIEWED
- _Procedure: The ExteriorLightingSafetyZb1 receive the following signals:
  Master Light Switch Resistor Ladder 1 (AN14_PI2)
  DcuMonTemperatureSafetyMaskZb1
  NIgnitionStatus
- _Pass criteria: Make Sure ExteriorLightingSafetyZb1 is receiving following signals
  Master Light Switch Resistor Ladder 1 (AN14_PI2)
  DcuMonTemperatureSafetyMaskZb1
  NIgnitionStatus
- _Regression: No
- _Time [hr]: 0.1
- _Test environment: Lab-Car (manual)

## STC-BDY02-1393: HW failures BMasterLightSwitchFaultStatusFuSa (OC)
The ExteriorLightingSafetyZb1 detect HW failures (i.e. short to ground, open, short to battery, out of range) on the signal BMasterLightSwitchFaultStatusFuSa within DTI = 200ms.
- _Object type: Misuse Test
- _Status: REVIEWED
- _Procedure: HW failures (i.e. short to ground, open, short to battery, out of range) on Master LIght Switch
- _Pass criteria: Verify that BMasterLightSwitchFaultStatusFuSa = active
- _Regression: No
- _Time [hr]: 0.1
- _Test environment: HIL (manual)

## STC-BDY02-1534: HW failures BMasterLightSwitchFaultStatusFuSa (OOR)
The ExteriorLightingSafetyZb1 detect when the singal BMasterLightSwitchFaultStatusFuSa falls out of the valid ranges as defined in [1394] DTI = 200ms.
- _Object type: Misuse Test
- _Status: REVIEWED
- _Procedure: Out of range
- _Pass criteria: Verify that BMasterLightSwitchFaultStatusFuSa = active
- _Regression: No
- _Time [hr]: 0.1
- _Test environment: HIL (manual)

## STC-BDY02-1535: BMasterLightSwitchFaultStatusFuSa Status
Upon detection of [1339] or [1726], the ExteriorLightingSafetyZb1 set BMasterLightSwitchFaultStatusFuSa to Active wihtin FRT = 100ms.
- _Object type: Misuse Test
- _Status: REVIEWED
- _Procedure: HW failures (i.e. short to ground, open, short to battery, out of range) or out of range
- _Pass criteria: Verify that BMasterLightSwitchFaultStatusFuSa = active within FRT =100ms and EflcSafetyStatusMask = bit2 to 3
- _Regression: No
- _Time [hr]: 0.1
- _Test environment: HIL (manual)

## STC-BDY02-1532: Command Signal
Signal Check
- _Object type: Misuse Test
- _Status: REVIEWED
- _Procedure: The ExteriorLightingSafetyZb1 command the following signals:
  Headlamp_Relay_2_Ctrl2 (HSD9_1)
- _Pass criteria: Verify that the ExteriorLightingSafetyZb1 command the signal.
- _Regression: No
- _Time [hr]: 0.1
- _Test environment: HIL (manual)

## STC-BDY02-1536: E2E Protection 1
Signals Check
- _Object type: Misuse Test
- _Status: REVIEWED
- _Procedure: The ExteriorLightingSafetyZb1 command the following signals to the ExteriorLightingSafetyZa1 and ExteriorLightingSafetyZc1:
  EflcSafetyStatusMask
  NMasterLightSwitchStatusFuSa
  BMasterLightSwitchFaultStatusFuSa
- _Pass criteria: Verify that the ExteriorLightingSafetyZb1 command the signals and that the message containing the signal specified EflcSafetyStatusMask is protected with an E2E protection mechanism.
- _Regression: No
- _Time [hr]: 0.1
- _Test environment: HIL (manual)

## STC-BDY02-1396: HW Fault on Headlamp_Relay_2_Ctrl
The ExteriorLightingSafetyZb1 detect HW failures (i.e. short to ground, open, short to battery, out of range) on the signal Headlamp_Relay_2_Ctrl within DTI = 200ms.
- _Object type: Misuse Test
- _Status: REVIEWED
- _Procedure: HW Fault on Headlamp_Relay_2_Ctrl (HB5A)
- _Pass criteria: Verify that EflcSafetyStatusMask = bit 4 to 7
- _Regression: No
- _Time [hr]: 0.1
- _Test environment: HIL (manual)

## STC-BDY02-1538: HW Fault on Headlamp_Relay_2_Ctrl
Upon detection of [STC-BDY02-1396], the ExteriorLightingSafetyZb1 set EflcSafetyStatusMask = bit 4 to 7 wihtin FRT = 100ms
- _Object type: Misuse Test
- _Status: REVIEWED
- _Procedure: HW Fault on Headlamp_Relay_2_Ctrl (HB5A)
- _Pass criteria: Verify that EflcSafetyStatusMask = bit 4 to 7
- _Regression: No
- _Time [hr]: 0.1
- _Test environment: HIL (manual)

## STC-BDY02-1399: SW Composition ExteriorLightingSafetyZc1
Composition Check
- _Object type: Misuse Test
- _Status: REVIEWED
- _Procedure: The SW composition ExteriorLightingSafetyZc1 implementing the safety monitoring of this function is designed.
- _Pass criteria: Verify that the SW composition is the only connected to the actuations of the outputs.
- _Regression: No
- _Time [hr]: 0.1
- _Test environment: HIL (manual)

## STC-BDY02-1539: SW Composition Brake/Tail Light Contro
Composition Check
- _Object type: Misuse Test
- _Status: REVIEWED
- _Procedure: The SW composition Brake/Tail Light Control is defined.
- _Pass criteria: Verify that the compositions Master Light Control is not connected to any actuation of the outputs.
- _Regression: No
- _Time [hr]: 0.1
- _Test environment: HIL (manual)

## STC-BDY02-1402: Stop Tail Command
Command Check
- _Object type: Misuse Test
- _Status: REVIEWED
- _Procedure: The ExteriorLightingSafetyZc1 command
  Stop_Tail_Outboard_PWR_RH (HSD3)
  Stop_Tail_Inboard_PWR_RH (HSD4)
  Stop_Tail_Outboard_PWR_LH (HSD8)
  Stop_Tail_Inboard_PWR_LH (HSD7)
  as requested by
  NLHTailInboardLampActivate_Req
  NLHTailOutboardLampActivate_Req
  NRHTailInboardLampActivate_Req
  NRHTailOutboardLampActivate_Req
- _Pass criteria: Verify that the command is at all times.
- _Regression: No
- _Time [hr]: 0.1
- _Test environment: HIL (manual)

## STC-BDY02-1540: BrakeLightConditionHappen Status 1
The ExteriorLightingSafetyZc1 set BrakeLightConditionHappen to true when either of the following occurs:
Brake Pedal is pressed (NBrakepedalStatus_Q == Valid && NBrakepedalStatus == Pressed)
Deceleration is above LongActiveThreshold calibratable ( gLongitudinal < -1.3 m/s2 only && gLongitudinal_Q = Valid)
- _Object type: Misuse Test
- _Status: REVIEWED
- _Procedure: Test Steps :
  NBrakepedalStatus_Q == Valid && NBrakepedalStatus == Pressed
  NgLongitudinal_Q == Valid && gLongitudinal < -1.3 m/s2
- _Pass criteria: Verify that BrakeLightConditionHappen =True.
- _Regression: No
- _Time [hr]: 0.1
- _Test environment: HIL (manual)

## STC-BDY02-1541: BrakeLightConditionHappen Status 2
The ExteriorLightingSafetyZc1 shall set BrakeLightConditionHappen to true when all the following occurs:
NBrakepedalStatus_Q != Valid
NpBrake_Q == Valid
pBrake > pBrakeThresholdActive
- _Object type: Misuse Test
- _Status: REVIEWED
- _Procedure: NBrakepedalStatus_Q != Valid && NpBrake_Q == Valid && pBrake >= pBrakeThresholdActive
- _Pass criteria: Verify that BrakeLightConditionHappen =True.
- _Regression: No
- _Time [hr]: 0.1
- _Test environment: HIL (manual)

## STC-BDY02-1542: Stop Tail Duty Cycle
Lamp Intensity Check
- _Object type: Misuse Test
- _Status: REVIEWED
- _Procedure: The ExteriorLightingSafetyZc1 set the duty cycle of the outputs :
  Stop_Tail_Outboard_PWR_RH (HSD3)
  Stop_Tail_Inboard_PWR_RH (HSD4)
  Stop_Tail_Outboard_PWR_LH (HSD8)
  Stop_Tail_Inboard_PWR_LH (HSD7)
  as requested by
  NTailInboardLampIntensity_Req
  NTailOutboardLampIntensity_Req
- _Pass criteria: Verify that the command is at all times.
- _Regression: No
- _Time [hr]: 0.1
- _Test environment: HIL (manual)

## STC-BDY02-1404: Command Brake Light 1
The ExteriorLightingSafetyZc1 detect when:
BrakeLightConditionHappen is set to true;
AND
NLHTailInboardLampActivate_Req = 'no request' AND
NLHTailOutboardLampActivate_Req = 'no request' AND
NRHTailInboardLampActivate_Req = 'no request' AND
NRHTailOutboardLampActivate_Req = 'no request'; AND
NIgnitionStatus ==0x5 (Ignition)
within DTI = 100ms.
- _Object type: Misuse Test
- _Status: REVIEWED
- _Procedure: Test Steps :
  BrakeLightConditionHappen is set to true
  NLHTailInboardLampActivate_Req = 'no request'
  NLHTailOutboardLampActivate_Req = 'no request'
  NRHTailInboardLampActivate_Req = 'no request'
  NRHTailOutboardLampActivate_Req = 'no request'
  NIgnitionStatus ==0x5 (Ignition)
  within DTI = 100ms.
- _Pass criteria: Verify that the Command brake light :
  Stop_Tail_Outboard_PWR_RH (HSD3)
  Stop_Tail_Inboard_PWR_RH (HSD4)
  Stop_Tail_Outboard_PWR_LH (HSD8)
  Stop_Tail_Inboard_PWR_LH (HSD7)
- _Regression: No
- _Time [hr]: 0.1
- _Test environment: HIL (manual)

## STC-BDY02-1543: Safe State #BDY02_RL_1
Upon detection of [STC-BDY02-1404] the ExteriorLightingSafetyZc1 transition to Safe State #BDY02_RL_1.
- _Object type: Misuse Test
- _Status: REVIEWED
- _Procedure: Test Steps :
  BrakeLightConditionHappen is set to true
  NLHTailInboardLampActivate_Req = 'no request'
  NLHTailOutboardLampActivate_Req = 'no request'
  NRHTailInboardLampActivate_Req = 'no request'
  NRHTailOutboardLampActivate_Req = 'no request'
  NIgnitionStatus ==0x5 (Ignition)
  within DTI = 100ms.
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)
- _Regression: No
- _Time [hr]: 0.1
- _Test environment: HIL (manual)

## STC-BDY02-1544: Command Brake Light 2
The ExteriorLightingSafetyZc1 detect when:
NMasterLightSwitchStatusFuSa != 0x0 (OFF)
AND
BrakeLightConditionHappen is set false AND
NLHTailInboardLampActivate_Req = 'no request' AND
NLHTailOutboardLampActivate_Req = 'no request' AND
NRHTailInboardLampActivate_Req = 'no request' AND
NRHTailOutboardLampActivate_Req = 'no request'; AND
NIgnitionStatus ==0x5 (Ignition)
within DTI = 100ms.
- _Object type: Misuse Test
- _Status: REVIEWED
- _Procedure: Test Steps :
  NMasterLightSwitchStatusFuSa != 0x0 (OFF)
  BrakeLightCondition is set false
  NLHTailInboardLampActivate_Req = 'no request'
  NLHTailOutboardLampActivate_Req = 'no request'
  NRHTailInboardLampActivate_Req = 'no request'
  NRHTailOutboardLampActivate_Req = 'no request'
  NIgnitionStatus ==0x5 (Ignition)
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)
  within 100ms
- _Regression: No
- _Time [hr]: 0.1
- _Test environment: HIL (manual)

## STC-BDY02-1545: Command Brake Light 3
The ExteriorLightingSafetyZc1 detect when:
BMasterLightSwitchFaultStatusFuSa = 0x1 (TRUE STATE meaning ACTIVE FAULT)
AND
BrakeLightConditionHappen is set false AND
NLHTailInboardLampActivate_Req = 'no request' AND
NLHTailOutboardLampActivate_Req = 'no request' AND
NRHTailInboardLampActivate_Req = 'no request' AND
NRHTailOutboardLampActivate_Req = 'no request';AND
NIgnitionStatus ==0x5 (Ignition)
within DTI = 100ms.
- _Object type: Misuse Test
- _Status: REVIEWED
- _Procedure: Test Steps :
  BMasterLightSwitchFaultStatusFuSa = Active
  BrakeLightCondition is set false
  NLHTailInboardLampActivate_Req = 'no request'
  NLHTailOutboardLampActivate_Req = 'no request'
  NRHTailInboardLampActivate_Req = 'no request'
  NRHTailOutboardLampActivate_Req = 'no request'
  NIgnitionStatus ==0x5 (Ignition)
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)
  within 100ms
- _Regression: No
- _Time [hr]: 0.1
- _Test environment: HIL (manual)

## STC-BDY02-1546: Safe State #BDY02_RL_2
Upon detection of [STC-BDY02-1544] or [STC-BDY02-1545] the ExteriorLightingSafetyZc1 transition to Safe State #BDY02_RL_2.
- _Object type: Misuse Test
- _Status: REVIEWED
- _Procedure: Test Steps :
  BMasterLightSwitchFaultStatusFuSa = Active
  BrakeLightCondition is set false
  NLHTailInboardLampActivate_Req = 'no request'
  NLHTailOutboardLampActivate_Req = 'no request'
  NRHTailInboardLampActivate_Req = 'no request'
  NRHTailOutboardLampActivate_Req = 'no request'
  NIgnitionStatus ==0x5 (Ignition)
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)
- _Regression: No
- _Time [hr]: 0.1
- _Test environment: HIL (manual)

## STC-BDY02-1547: Command Brake Light 4 (88%)
The ExteriorLightingSafetyZc1 detect when:
BMasterLightSwitchFaultStatusFuSa = 0x1 (TRUE STATE meaning ACTIVE FAULT) OR NMasterLightSwitchStatusFuSa != 0x0 (OFF) AND
(NTailInboardLampIntensity_Req <65% OR NTailInboardLampIntensity_Req <65%) AND
NIgnitionStatus ==0x5 (Ignition)
within DTI = 100ms.
- _Object type: Misuse Test
- _Status: REVIEWED
- _Procedure: Rear Light request active
- _Pass criteria: Verify that the Command 88% :
  Stop_Tail_Outboard_PWR_RH (HSD3)
  Stop_Tail_Inboard_PWR_RH (HSD4)
  Stop_Tail_Outboard_PWR_LH (HSD8
  Stop_Tail_Inboard_PWR_LH (HSD7)
  within 100ms
- _Regression: No
- _Time [hr]: 0.1
- _Test environment: HIL (manual)

## STC-BDY02-1548: Safe State #BDY02_RL_2
Upon detection of [STC-BDY02-1544] or [STC-BDY02-1545] the ExteriorLightingSafetyZc1 transition to Safe State #BDY02_RL_2.
- _Object type: Misuse Test
- _Status: REVIEWED
- _Procedure: Rear Light request active
- _Pass criteria: Verify that the Command 88% :
  Stop_Tail_Outboard_PWR_RH (HSD3)
  Stop_Tail_Inboard_PWR_RH (HSD4)
  Stop_Tail_Outboard_PWR_LH (HSD8
  Stop_Tail_Inboard_PWR_LH (HSD7)
- _Regression: No
- _Time [hr]: 0.1
- _Test environment: HIL (manual)

## STC-BDY02-1549: Command Brake Light 5 (100%)
The ExteriorLightingSafetyZc1 detect when:
BrakeLightConditionHappen is set TRUE AND
(NTailInboardLampIntensity_Req <65% OR NTailOutboardLampIntensity_Req <65%)
within DTI = 100ms.
- _Object type: Misuse Test
- _Status: REVIEWED
- _Procedure: Brake Light condition is true
- _Pass criteria: Verify that the Command 100% :
  Stop_Tail_Outboard_PWR_RH (HSD3)
  Stop_Tail_Inboard_PWR_RH (HSD4)
  Stop_Tail_Outboard_PWR_LH (HSD8
  Stop_Tail_Inboard_PWR_LH (HSD7)
  within 100ms
- _Regression: No
- _Time [hr]: 0.1
- _Test environment: HIL (manual)

## STC-BDY02-1550: Safe State #BDY02_RL_1
Upon detection of [STC-BDY02-1544] or [STC-BDY02-1545] the ExteriorLightingSafetyZc1 transition to Safe State #BDY02_RL_1.
- _Object type: Misuse Test
- _Status: REVIEWED
- _Procedure: Brake Light condition is true
- _Pass criteria: Verify that the Command 100% :
  Stop_Tail_Outboard_PWR_RH (HSD3)
  Stop_Tail_Inboard_PWR_RH (HSD4)
  Stop_Tail_Outboard_PWR_LH (HSD8
  Stop_Tail_Inboard_PWR_LH (HSD7)
- _Regression: No
- _Time [hr]: 0.1
- _Test environment: HIL (manual)

## STC-BDY02-1551: No reaction with critical temperature
No action is to be taken when DcuMonTemperatureSafetyMaskZc1 = Critical temperature threshold.
- _Object type: Misuse Test
- _Status: REVIEWED
- _Procedure: DcuMonTemperatureSafetyMaskZC1 = Critical temperature
- _Pass criteria: No reaction
- _Regression: No
- _Time [hr]: 0.1
- _Test environment: HIL (manual)

## STC-BDY02-1407: High Side Command Stop Tail Light with with 100% duty
Stop Tail Light command
- _Object type: Misuse Test
- _Status: REVIEWED
- _Procedure: The ExteriorLightingSafetyZc1 command 100% the outputs:
  Stop_Tail_Outboard_PWR_RH (HSD3)
  Stop_Tail_Inboard_PWR_RH (HSD4)
  Stop_Tail_Outboard_PWR_LH (HSD8)
  Stop_Tail_Inboard_PWR_LH (HSD7)
- _Pass criteria: Verify that Stop Tail Light are commanded.
- _Regression: No
- _Time [hr]: 0.1
- _Test environment: HIL (manual)

## STC-BDY02-1552: High Side Command Stop Tail Light with with 88% duty
- _Object type: Misuse Test
- _Status: REVIEWED
- _Procedure: The ExteriorLightingSafetyZc1 command 88% the outputs:
  Stop_Tail_Outboard_PWR_RH (HSD3)
  Stop_Tail_Inboard_PWR_RH (HSD4)
  Stop_Tail_Outboard_PWR_LH (HSD8)
  Stop_Tail_Inboard_PWR_LH (HSD7)
- _Pass criteria: Verify that Stop Tail Light are commanded.
- _Regression: No
- _Time [hr]: 0.1
- _Test environment: HIL (manual)

## STC-BDY02-1553: NRlcSafetyClusterMessage Fault
Signal Check
- _Object type: Misuse Test
- _Status: REVIEWED
- _Procedure: The ExteriorLightingSafetyZc1 command the below signal:
  NRlcSafetyClusterMessage = "fault value"
- _Pass criteria: Verify that the signal is in fault.
- _Regression: No
- _Time [hr]: 0.1
- _Test environment: HIL (manual)

## STC-BDY02-1410: Brake Light request
While in Safe State #BDY02_RL_1, the ExteriorLightingSafetyZc1 perform the action specified in [1648] within FRT = 100 ms.
- _Object type: Misuse Test
- _Status: REVIEWED
- _Procedure: Test Steps :
  BrakeLightConditionHappen is set to true;
  &&
  NRHTailLampActivate_Req =no request; &&
  NLHTailLampActivate_Req = norequest;
  OR
  Communication Error on any of the below signals :
  - NBrakePedalSwitch1Status
  NBrakePedalSwitch2Status
  pBrake
  gLongitudinal
  NgLongitudinal_Q
- _Pass criteria: Verify the Brake Light requested.
  within 100ms
- _Regression: No
- _Time [hr]: 0.1
- _Test environment: HIL (manual)

## STC-BDY02-1554: Exit Safe State #BDY02_1
The ExteriorLightingSafetyZc1 exit Safe State #BDY02_RL_1 at the new vehicle ignition cycle or after a healing time interval, HTI= 3 secs, when the fault no longer exists.
- _Object type: Misuse Test
- _Status: REVIEWED
- _Procedure: Next ignition cycle
- _Pass criteria: Verify the Exit Safe State #BDY02_1 and Normal Operation of ElcSafety.
- _Regression: No
- _Time [hr]: 0.1
- _Test environment: HIL (manual)

## STC-BDY02-1555: Tail light activation
While in Safe State #BDY02_RL_2, the ExteriorLightingSafetyZc1 perform the action specified in [1649] within FRT = 100 ms.
- _Object type: Misuse Test
- _Status: REVIEWED
- _Procedure: Test Steps :
  Master Light switch status = Step4 && BLH_DipperBeamActivate_Req = No activation request & BRH_DippedBeamActivate_Req = No activation request
  HW failures (i.e. short to ground, open, short to battery, out of range) on the signal specified in [1334]
- _Pass criteria: Verify the tail light activated
  within 100ms
- _Regression: No
- _Time [hr]: 0.1
- _Test environment: HIL (manual)

## STC-BDY02-1413: Exit Safe State #BDY02_2
The ExteriorLightingSafetyZc1 exit Safe State #BDY02_RL_2 at the new vehicle ignition cycle or after a healing time interval, HTI= 3 secs, when the fault no longer exists.
- _Object type: Misuse Test
- _Status: REVIEWED
- _Procedure: Next Ignition Cycle
- _Pass criteria: Verify the Exit Safe State #BDY02_2 and Normal Operation of ElcSafety
- _Regression: No
- _Time [hr]: 0.1
- _Test environment: HIL (manual)

## STC-BDY02-1556: Brake Light/Tail Ligt warning
While in Safe State #BDY02_RL_3, the ExteriorLightingSafetyZc1 perform the action specified in [1653] within FRT = 100 ms.
- _Object type: Misuse Test
- _Status: REVIEWED
- _Procedure: HW Fault in :
  Stop_Tail_Outboard_PWR_RH (HSD3)
  Stop_Tail_Inboard_PWR_RH (HSD4)
  Stop_Tail_Outboard_PWR_LH (HSD8)
  Stop_Tail_Inboard_PWR_LH (HSD7)
- _Pass criteria: Verify the Warning sent to driver (Brake Light/Tail Ligt warning)
  within 100ms
- _Regression: No
- _Time [hr]: 0.1
- _Test environment: HIL (manual)

## STC-BDY02-1416: Exit Safe State #BDY02_4
The ExteriorLightingSafetyZc1 exit Safe State #BDY02_RL_3 at the new vehicle ignition cycle or after a healing time interval, HTI= 3 secs, when the fault no longer exists.
- _Object type: Misuse Test
- _Status: REVIEWED
- _Procedure: Next Ignition Cycle
- _Pass criteria: Exit Safe State #BDY02_4 and Normal Operation of ElcSafety
- _Regression: No
- _Time [hr]: 0.1
- _Test environment: HIL (manual)

## STC-BDY02-1557: E2E Protection for input signals 1
Signals Check
- _Object type: Misuse Test
- _Status: REVIEWED
- _Procedure: The ExteriorLightingSafetyZc1 receive the following signals:
  NBrakePedalStatus
  NBrakePedalStatus_Q
  pBrake
  pBrake_Q
  gLongitudinal
  NgLongitudinal_Q
- _Pass criteria: Verify that the message containing the signals is protected with an E2E protection mechanism.
- _Regression: No
- _Time [hr]: 0.1
- _Test environment: HIL (manual)

## STC-BDY02-1558: Request Received Signals
Signals Check
- _Object type: Misuse Test
- _Status: REVIEWED
- _Procedure: The ExteriorLightingSafetyZc1 receive the following signals:
  NLHTailInboardLampActivate_Req
  NLHTailOutboardLampActivate_Req
  NRHTailInboardLampActivate_Req
  NRHTailOutboardLampActivate_Req
  NTailInboardLampIntensity_Req
  NTailOutboardLampIntensity_Req
  DcuMonTemperatureSafetyMaskZc1
- _Pass criteria: Verify that the request signals are received.
- _Regression: No
- _Time [hr]: 0.1
- _Test environment: HIL (manual)

## STC-BDY02-1559: E2E Protection for input signals 2
Signals Check
- _Object type: Misuse Test
- _Status: REVIEWED
- _Procedure: The ExteriorLightingSafetyZc1 shall receive the following signals:
  NMasterLightSwitchStatusFuSa
  BMasterLightSwitchFaultStatusFuSa
  EflcSafetyStatusMask
  NIgnitionStatus
- _Pass criteria: Verify that the message containing the signals is protected with an E2E protection mechanism.
- _Regression: No
- _Time [hr]: 0.1
- _Test environment: HIL (manual)

## STC-BDY02-1420: Brake Light Requested (1)
The ExteriorLightingSafetyZc1 detect if a communication error occurs in the transmission of the signals specified in [1686], [1688] within DTI = 200ms.
- _Object type: Misuse Test
- _Status: REVIEWED
- _Procedure: Communication Error on any of the below signals :
  NBrakePedalStatus
  pBrake
  gLongitudinal
  NgLongitudinal_Q
- _Pass criteria: Verify the Brake Light Requested
  within 200 ms
- _Regression: No
- _Time [hr]: 0.1
- _Test environment: HIL (manual)

## STC-BDY02-1560: Safe State #BDY02_RL_1 (1)
Upon detection of [1696] the ExteriorLightingSafetyZc1 transition to Safe State #BDY02_RL_1.
- _Object type: Misuse Test
- _Status: REVIEWED
- _Procedure: Communication Error on any of the below signals :
  NBrakePedalStatus
  pBrake
  gLongitudinal
  NgLongitudinal_Q
- _Pass criteria: Verify the Brake Light Requested
- _Regression: No
- _Time [hr]: 0.1
- _Test environment: HIL (manual)

## STC-BDY02-1561: Tail light activation 1
The ExteriorLightingSafetyZc1 detect if a communication error occurs in the transmission of the signals specified in [1691] within DTI = 200ms.
- _Object type: Misuse Test
- _Status: REVIEWED
- _Procedure: Communication Error on any of the below signals :
  NMasterLightSwitchStatusFuSa
  BMasterLightSwitchFaultStatusFuSa
- _Pass criteria: Verify the tail light activation
  within 200ms
- _Regression: No
- _Time [hr]: 0.1
- _Test environment: HIL (manual)

## STC-BDY02-1562: Safe State #BDY02_RL_2 (1)
Upon detection of [1733] the ExteriorLightingSafetyZc1 transition to Safe State #BDY02_RL_2.
- _Object type: Misuse Test
- _Status: REVIEWED
- _Procedure: Communication Error on any of the below signals :
  NMasterLightSwitchStatusFuSa
  BMasterLightSwitchFaultStatusFuSa
- _Pass criteria: Verify the tail light activation
- _Regression: No
- _Time [hr]: 0.1
- _Test environment: HIL (manual)

## STC-BDY02-1563: Tail light activation 2
The ExteriorLightingSafetyZc1 detect if a communication error occurs in the transmission of the signals specified in [1817] AND
(( NMasterLightSwitchStatusFuSa != 0x0 (OFF) OR (BMasterLightSwitchFaultStatusFuSa = 0x1 (TRUE STATE meaning ACTIVE FAULT)) AND BrakeLightConditionHappen is set false) within DTI = 200ms.
- _Object type: Misuse Test
- _Status: REVIEWED
- _Procedure: Communication Error on any of the below signals :
  NignitionStatus
  No Tail Light Request
  Brakelightcondition is false
- _Pass criteria: Verify the tail light activation
- _Regression: No
- _Time [hr]: 0.1
- _Test environment: HIL (manual)

## STC-BDY02-1564: Safe State #BDY02_RL_2 (2)
Upon detection of [STC-BDY02-1563] the ExteriorLightingSafetyZc1 shall transition to Safe State #BDY02_RL_2.
- _Object type: Misuse Test
- _Status: REVIEWED
- _Procedure: Communication Error on any of the below signals :
  NignitionStatus
  No Tail Light Request
  Brakelightcondition is false
- _Pass criteria: Verify the tail light activation
- _Regression: No
- _Time [hr]: 0.1
- _Test environment: HIL (manual)

## STC-BDY02-1565: Brake Light Requested (2)
The ExteriorLightingSafetyZc1 detect if a communication error occurs in the transmission of the signals specified in [1817] AND BrakeLightConditionHappen is set TRUE within DTI = 200ms.
- _Object type: Misuse Test
- _Status: REVIEWED
- _Procedure: Communication Error on any of the below signals :
  NignitionStatus
  No Tail Light Request
  Brakelightcondition is true
- _Pass criteria: Verify the Brake Light Requested
  within 200ms
- _Regression: No
- _Time [hr]: 0.1
- _Test environment: HIL (manual)

## STC-BDY02-1566: Safe State #BDY02_RL_1 (2)
Upon detection of [STC-BDY02-1565] the ExteriorLightingSafetyZc1 transition to Safe State #BDY02_RL_1.
- _Object type: Misuse Test
- _Status: REVIEWED
- _Procedure: Communication Error on any of the below signals :
  NignitionStatus
  No Tail Light Request
  Brakelightcondition is true
- _Pass criteria: Verify the Brake Light Requested
- _Regression: No
- _Time [hr]: 0.1
- _Test environment: HIL (manual)

## STC-BDY02-1567: Brake Light Requested (3)
The ExteriorLightingSafetyZc1 detect within DTI = 200ms if:
(pBrake_Q != valid && NBrakepedalStatus_Q != valid ) || gLongitudinal_Q != valid
- _Object type: Misuse Test
- _Status: REVIEWED
- _Procedure: Test Step :
  (pBrake_Q != valid && NBrakepedalStatus_Q != valid ) || gLogitudinal_Q != valid
- _Pass criteria: Verify the Brake Light Requested
- _Regression: No
- _Time [hr]: 0.1
- _Test environment: HIL (manual)

## STC-BDY02-1568: Safe State #BDY02_RL_1 (3)
Upon detection of [STC-BDY02-1567] the ExteriorLightingSafetyZc1 shall transition to Safe State #BDY02_RL_1.
- _Object type: Misuse Test
- _Status: REVIEWED
- _Procedure: Test Step :
  (pBrake_Q != valid && NBrakepedalStatus_Q != valid ) || gLogitudinal_Q != valid
- _Pass criteria: Verify the Brake Light Requested
- _Regression: No
- _Time [hr]: 0.1
- _Test environment: HIL (manual)

## STC-BDY02-1569: Command Sent Signals
Signals Check
- _Object type: Misuse Test
- _Status: REVIEWED
- _Procedure: The ExteriorLightingSafetyZc1 command the following signals:
  Stop_Tail_Outboard_PWR_RH (HSD3)
  Stop_Tail_Inboard_PWR_RH (HSD4)
  Stop_Tail_Outboard_PWR_LH (HSD8
  Stop_Tail_Inboard_PWR_LH (HSD7)
- _Pass criteria: Verify that the command signals are sent.
- _Regression: No
- _Time [hr]: 0.1
- _Test environment: HIL (manual)

## STC-BDY02-1570: E2E Protection for output signals
Signals Check
- _Object type: Misuse Test
- _Status: REVIEWED
- _Procedure: The ExteriorLightingSafetyZc1 shall command the following signal to ADI
  NRlcSafetyClusterMessage
  RlcSafetyStatusMask
- _Pass criteria: Verify that the message containing the signals is protected with an E2E protection mechanism.
- _Regression: No
- _Time [hr]: 0.1
- _Test environment: HIL (manual)

## STC-BDY02-1571: Brake Light/Tail Light warning sent to driver
The ExteriorLightingSafetyZc1 detect HW failures (i.e. short to ground, open, short to battery, out of range) on the signal specified in [1705] within DTI = 200ms.
- _Object type: Misuse Test
- _Status: REVIEWED
- _Procedure: HW Fault on :
  Stop_Tail_Outboard_PWR_RH (HSD3)
  Stop_Tail_Inboard_PWR_RH (HSD4)
  Stop_Tail_Outboard_PWR_LH (HSD8)
  Stop_Tail_Inboard_PWR_LH (HSD7)
- _Pass criteria: Verify that the Warning sent to driver (Brake Light/Tail Light warning)
  within 200ms
- _Regression: No
- _Time [hr]: 0.1
- _Test environment: HIL (manual)

## STC-BDY02-1572: Safe State #BDY02_RL_3
Upon detection of [STC-BDY02-1571], the ExteriorLightingSafetyZc1 transition to Safe State #BDY02_RL_3.
- _Object type: Misuse Test
- _Status: REVIEWED
- _Procedure: HW Fault on :
  Stop_Tail_Outboard_PWR_RH (HSD3)
  Stop_Tail_Inboard_PWR_RH (HSD4)
  Stop_Tail_Outboard_PWR_LH (HSD8)
  Stop_Tail_Inboard_PWR_LH (HSD7)
- _Pass criteria: Verify that the Warning sent to driver (Brake Light/Tail Light warning)
- _Regression: No
- _Time [hr]: 0.1
- _Test environment: HIL (manual)

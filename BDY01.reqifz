# BDY01

# Specification: BDY01

## STC-BDY02-446: Main beam telltale ON (ID:STC-HMI01-214)
Main beam ISO symbol shall be displayed to the driver when main beam latched function is active
- _Object type: Cross Functional Test
- _Status: REVIEWED
- _Procedure: 1.Set ignition state=5
  2.Set Master Light Switch Position = 2
  3.Active main beam latched function by pushing the DIMS stalk forwards to a latched position
- _Pass criteria: NFlashMainSwitch = (0x2),Main_Beam_Latched_ Available.
  Main beam ISO symbol shall be displayed on the driver display
- _Regression: Yes
- _Time [hr]: 0.2
- _Test environment: Lab-Car (manual)

## STC-BDY02-447: Main beam telltale OFF (ID:STC-HMI01-215)
Main beam ISO symbol shall be OFF on the driver when main beam latched function is NOT active
- _Object type: Cross Functional Test
- _Status: REVIEWED
- _Procedure: 1.Set ignition state<5
  2.Set Master Light Switch Position = 2
  3.Active main beam latched function by pushing the DIMS stalk forwards to a latched position
- _Pass criteria: NFlashMainSwitch = (0x0),Main_Beam_Latched_ Unavailable.
  Main beam ISO symbol shall be OFF on the driver display
- _Regression: Yes
- _Time [hr]: 0.2
- _Test environment: Lab-Car (manual)

## STC-BDY02-448: Main beam telltale OFF
Main beam ISO symbol shall be OFF on the driver when main beam latched function is NOT active
- _Object type: Negative Test
- _Status: REVIEWED
- _Procedure: 1.Set ignition state=5
  2.Set Master Light Switch Position = 0||1
  3.Active main beam latched function by pushing the DIMS stalk forwards to a latched position
- _Pass criteria: NFlashMainSwitch = (0x0),Main_Beam_Latched_ Unavailable.
  Main beam ISO symbol shall be OFF on the driver display
- _Regression: Yes
- _Time [hr]: 0.2
- _Test environment: Lab-Car (manual)

## STC-BDY02-449: Main beam telltale ON
Main beam ISO symbol shall be graphically displayed to the driver when main beam flash function is active
- _Object type: Nominal Test
- _Status: REVIEWED
- _Procedure: 1.Set ignition state >= 2
  2.Active main beam flash function by pulling the DIMS stalk towards the steering wheel to a momentary position
- _Pass criteria: NFlashMainSwitch = (0x1),Main_Beam_Flash_ Available.
  Main beam ISO symbol shall be displayed on the driver display
- _Regression: Yes
- _Time [hr]: 0.2
- _Test environment: Lab-Car (manual)

## STC-BDY02-450: Main beam telltale OFF
Main beam ISO symbol shall be graphically displayed to the driver when main beam flash function is NOT active
- _Object type: Negative Test
- _Status: REVIEWED
- _Procedure: 1.Set ignition state < 2
  2.Active main beam flash function by pulling the DIMS stalk towards the steering wheel to a momentary position
- _Pass criteria: 2.NFlashMainSwitch = (0x0),Main_Beam_Flash_ Inactive.
  Main beam ISO symbol shall be OFF on the driver display
- _Regression: Yes
- _Time [hr]: 0.2
- _Test environment: Lab-Car (manual)

## STC-BDY02-453: Main beam latched function available
Main beam latched function with master light position
- _Object type: Nominal Test
- _Status: REVIEWED
- _Procedure: 1.Set ignition state >= 5
  2.Set Master Light Switch Position = 2
- _Pass criteria: Main_Beam_Latched_ Available but not activated,
  NFlashMainSwitch = (0x0)
- _Regression: Yes
- _Time [hr]: 0.2
- _Test environment: Lab-Car (auto)

## STC-BDY02-455: Main beam latched function NOT available with igniton state
Main beam latched function NOT available when ignition state<5
- _Object type: Negative Test
- _Status: REVIEWED
- _Procedure: 1.Set ignition state <5
  2.Set Master Light Switch Position = 2
  3.Push the DIMS stalk forwards to a latched position
- _Pass criteria: Main beam latched function not available
- _Regression: Yes
- _Time [hr]: 0.2
- _Test environment: Lab-Car (auto)

## STC-BDY02-572: Main beam latched function NOT available with igniton state (ID:STC-ADA-02-08-530)
Main beam latched function NOT available when ignition state<5
- _Object type: Cross Functional Test
- _Status: REVIEWED
- _Procedure: 1.Set ignition state <5
  2.Set Master Light Switch Position = Auto
  3.Push the DIMS stalk forwards to a latched position
- _Pass criteria: Main beam latched function not available
- _Regression: Yes
- _Time [hr]: 0.2
- _Test environment: Lab-Car (auto)

## STC-BDY02-457: Main beam latched function deactivation with DIMS stalk
Deactivate main beam latched by pulling the DIMS stalk back from the latched position position
- _Object type: Nominal Test
- _Status: REVIEWED
- _Procedure:
  1. Set NIgnitionStatus >= 5
  2. Main Beam Latched Function Available && NFlashMainSwitch = (0x2)
  2.Pull the DIMS stalk back from the latched position
- _Pass criteria: 2.NFlashMainSwitch != (0x2),Main_Beam_Latched_ Inactive && NMainBeamStatus = Active
- _Regression: No
- _Time [hr]: 0.2
- _Test environment: Lab-Car (auto)

## STC-BDY02-458: Main beam latched function deactivation with ignition state
Deactivate main beam latched function with ignition state<5
- _Object type: Nominal Test
- _Status: REVIEWED
- _Procedure: 1.Activate main beam latched function i.e., NIgnitionStatus >= 5 && NFlashMainSwitch = (0x2)
  2.Set ignition state < 5
- _Pass criteria: 2.NMainBeamStatus = = Inactive
- _Regression: Yes
- _Time [hr]: 0.2
- _Test environment: Lab-Car (auto)

## STC-BDY02-1064: Main beam latched function deactivation with High severity
To cofirm ZB1 shall deactivate main beam latched when High severity crash occurs
- _Object type: Nominal Test
- _Status: REVIEWED
- _Procedure: 1.Activate main beam latched function i.e., NIgnitionStatus >= 5 && NFlashMainSwitch = (0x2)2.Simulate NCrashSeverity = High from ORC on Chassis CAN
- _Pass criteria: NMainBeamStatus = Inactive
- _Regression: No
- _Time [hr]: 0.2
- _Test environment: Lab-Car (auto)

## STC-BDY02-1065: Main beam latched function deactivation with low severity
To cofirm ZB1 shall deactivate main beam latched when Low severity crash occurs
- _Object type: Nominal Test
- _Status: REVIEWED
- _Procedure: 1.Activate main beam latched function i.e., NIgnitionStatus >= 5 && NFlashMainSwitch = (0x2)2.Simulate NCrashSeverity = Low from ORC on Chassis CAN
- _Pass criteria: NMainBeamStatus = Inactive
- _Regression: No
- _Time [hr]: 0.2
- _Test environment: Lab-Car (auto)

## STC-BDY02-459: Main beam latched function deactivation with master light
main beam latched function deactivation with master light switch position
- _Object type: Nominal Test
- _Status: REVIEWED
- _Procedure: 1.Activate main beam latched function i.e., NIgnitionStatus >= 5 && NFlashMainSwitch = (0x2)
  2.Set Master Light Switch Position = 0||1
- _Pass criteria: 2.NFlashMainSwitch = 0x0,Main_Beam_Latched_ Unavailable
- _Regression: No
- _Time [hr]: 0.2
- _Test environment: Lab-Car (auto)

## STC-BDY02-462: Main beam flash function activation
Main beam flash function activation with DIMS stalk
- _Object type: Nominal Test
- _Status: REVIEWED
- _Procedure: 1.Set ignition state = 2
  2.Pull the DIMS stalk towards the steering wheel to a momentary position
  3.Repeast step 2 for all ignition states 3,4,5 and 6
- _Pass criteria: Main_Beam_Flash_ Active.
  NFlashMainSwitch = (0x1)
- _Regression: No
- _Time [hr]: 0.2
- _Test environment: Lab-Car (auto)

## STC-BDY02-474: Main beam latched activation
Main beam fucntion activation
- _Object type: Nominal Test
- _Status: REVIEWED
- _Procedure: 1.Set ignition state>=5
  2.Enable main beam latched function by
  pushing the DIMS stalk forwards to a latched position
- _Pass criteria: Main beam latched activated
- _Regression: No
- _Time [hr]: 0.1
- _Test environment: Lab-Car (auto)

## STC-BDY02-574: Main beam flash function inactivation with release of DIMS stalk
Main beam flash function deactivation when ignition state<2
- _Object type: Nominal Test
- _Status: REVIEWED
- _Procedure: 1.Activate main beam flash function
  2.Release DIMS stalk while main flash function is in activation
- _Pass criteria: 2. NMainBeamStatus = Inactive
  NFlashMainSwitch != Flash
- _Regression: No
- _Time [hr]: 0.2
- _Test environment: Lab-Car (auto)

## STC-BDY02-1626: Main Beam Flash Function Deactivation
The main beam flash function shall be deactivated in the event of an ignition state transition to any state less than Ignition (5) or the state Connected Awake (7).
- _Object type: Nominal Test
- _Status: REVIEWED
- _Procedure:
  1. NIgnitionStatus = 5
  2. NMainBeamStatus = Active
  3. NIgnitionStatus < Ignition
  ||
  NIgnitionStatus == Connected Awake
- _Pass criteria: 3. NMainBeamStatus = Inactive

## STC-BDY02-1442: High Beam Short circuit fault
To confirm High Beam diagnostic strategy when short circuit fault occurs
- _Object type: Nominal Test
- _Status: REVIEWED
- _Procedure: 1.Creat High Beam circuit fault i.e., short circuit fault
  2.After fault, make sure the drive feedback curent is out of normal operation thresholds
- _Pass criteria: NHighBeamActiveStatus = Fault && NMainBeamClusterMessage = Fault display on ICU
- _Regression: No
- _Time [hr]: 0.1
- _Test environment: Lab-Car (manual)

## STC-BDY02-1446: High Beam Activation (ID:STC-ADA02-08-522)
To confirm High Beam activation
- _Object type: Cross Functional Test
- _Status: REVIEWED
- _Procedure: 1.Set Iginition State >=5
  2.Activate Main beam flash latched function or main beam flash function
- _Pass criteria: NHighBeamActiveStatus = Active
- _Regression: No
- _Time [hr]: 0.1
- _Test environment: Lab-Car (auto)

## STC-BDY02-1443: High Beam open circuit fault
To confirm High Beam diagnostic strategy when open circuit fault occurs
- _Object type: Nominal Test
- _Status: REVIEWED
- _Procedure: 1.Creat DTRL circuit fault i.e., open circuit fault
  2.After fault, make sure the drive feedback curent is out of normal operation thresholds
- _Pass criteria: NHighBeamActiveStatus = Fault && NMainBeamClusterMessage = Fault display on ICU
- _Regression: No
- _Time [hr]: 0.1
- _Test environment: Lab-Car (manual)

## STC-BDY02-1444: High Beam circuit circuit fault reset
To confirm High Beam lights fault reset with new ignition cycle
- _Object type: Nominal Test
- _Status: REVIEWED
- _Procedure: 1.Creat DTRL circuit fault i.e., Open circuit fault
  2.After fault, make sure the drive feedback curent is out of normal operation thresholds
  3.Start new ignition cycle
- _Pass criteria: NHighBeamActiveStatus = Inactive && NMainBeamClusterMessage = Fault display shall e cleared on ICU
- _Regression: No
- _Time [hr]: 0.1
- _Test environment: Lab-Car (manual)

## STC-BDY02-593: MasterLightSwitchResistorLadder1 voltage
To confirm MasterLightSwitchResistorLadder1 voltage to detect MLS position
- _Object type: Nominal Test
- _Status: REVIEWED
- _Procedure: 1.Change MasterLightSwitchResistorLadder1 voltage to STEP1 i.e., Nominal voltage(1.46),Min vol(1.43),Max(1.49)
  2.Change MasterLightSwitchResistorLadder1 voltage to STEP2 i.e., Nominal voltage(2.12),Min vol(2.08),Max(2.16)
  3.Change MasterLightSwitchResistorLadder1 voltage to STEP3 i.e., Nominal voltage(2.83),Min vol(2.78),Max(2.89)
  4.Change MasterLightSwitchResistorLadder1 voltage to STEP4 i.e., Nominal voltage(3.58),Min vol(3.51),Max(3.65)
  5.Change MasterLightSwitchResistorLadder1 voltage to previous state i.e.,Nominal voltage (4.26),Min vol(4.17),Max(4.35)
  6.Change MasterLightSwitchResistorLadder1 voltage to
  FAULT_MLS(Open circuit/Short to batt) i.e., Nominal voltage(5),Min vol(4.75),Max(5)
  7.Change MasterLightSwitchResistorLadder1 voltage to FAULT_MLS(Short to gnd) i.e., Nominal voltage(0),Min vol(0),Max(0.75)
  8.Change MasterLightSwitchResistorLadder1 voltage to FAULT_MLS(Out of range) i.e.,
  > 0.75 and < 1.43,
  > 1.49 and < 2.08,
  > 2.16 and < 2.78,
  > 2.89 and < 3.51,
  > 3.65 and < 4.17,
  > 4.35 and < 4.75
- _Pass criteria: 1.MLS position is set to Off_NMastrLghtSwtchPos
  2.MLS position is set to Auto_NMastrLghtSwtchPos
  3.MLS position is set to Side_Lamps_NMastrLghtSwtchPos
  4.MLS position is set to Dipped_Beam_NMastrLghtSwtchPos
  5.MLS position is set to Previous State
  6.MLS position is set to Auto_NMastrLghtSwtchPos
  7.MLS position is set to Auto_NMastrLghtSwtchPos
  8.MLS position is set to Auto_NMastrLghtSwtchPos
- _Regression: No
- _Time [hr]: 0.2
- _Test environment: Lab-Car (auto)

## STC-BDY02-594: MasterLightSwitchResistorLadder2 voltage
To confirm MasterLightSwitchResistorLadder2 voltage to detect MLS Fog request
- _Object type: Nominal Test
- _Status: REVIEWED
- _Procedure: 1.Change MasterLightSwitchResistorLadder2 voltage to STEP1 i.e., Nominal voltage(3.85),Min vol(3.77),Max(3.93)
  2.Change MasterLightSwitchResistorLadder2 voltage to STEP2 i.e., Nominal voltage(TBD),Min vol(TBD),Max(TBD)
  3.Change MasterLightSwitchResistorLadder2 voltage to STEP3 i.e., Nominal voltage(2.04),Min vol(2),Max(2.08)
  4.Change MasterLightSwitchResistorLadder2 voltage to
  FAULT_MLS(Open circuit/Short to batt) i.e., Nominal voltage(5),Min vol(4.75),Max(5)
  5.Change MasterLightSwitchResistorLadder2 voltage to FAULT_MLS(Short to gnd) i.e., Nominal voltage(0),Min vol(0),Max(0.75)
  6.Change MasterLightSwitchResistorLadder2 voltage to FAULT_MLS(Out of range) i.e.,
  > 0.75 and < 2.0
  > 2.08 and < 3.77
  > 3.93 and < 4.75
- _Pass criteria: 1.MLS fog reuest is set to OFF_BOffOnState(No press)
  2.MLS fog reuest is set to OFF_BOffOnState(Front fog)
  3.MLS fog reuest is set to ON_BOffOnState(Rear fog)
  4.MLS fog reuest is set to OFF_BOffOnState
  5.MLS fog reuest is set to OFF_BOffOnState
  6.MLS fog reuest is set to OFF_BOffOnState
- _Regression: No
- _Time [hr]: 0.25
- _Test environment: Lab-Car (auto)

## STC-BDY02-595: MLS fault display
To confirm the user display when MLS is faulty
- _Object type: Nominal Test
- _Status: REVIEWED
- _Procedure: 1.Set MLS to faulty state,
  Set MasterLightSwitchResistorLadder1 /MasterLightSwitchResistorLadder2 voltage to
  FAULT_MLS(Open circuit/Short to batt) i.e., Nominal voltage(5),Min vol(4.75),Max(5)
- _Pass criteria: ZB1 shall set 0x01 TBC DTC along with the fault display on DD
- _Regression: No
- _Time [hr]: 0.5
- _Test environment: Lab-Car (auto)

## STC-BDY02-1435: MasterLightSwitchResistorLadder1 voltage
To confirm MasterLightSwitchResistorLadder1 voltage to detect MLS position
- _Object type: Nominal Test
- _Status: REVIEWED
- _Procedure: 1.Change MasterLightSwitchResistorLadder1 voltage to STEP1 i.e., Nominal voltage(1.46),Min vol(1.43),Max(1.49)
  2.Change MasterLightSwitchResistorLadder1 voltage to STEP2 i.e., Nominal voltage(2.12),Min vol(2.08),Max(2.16)
  3.Change MasterLightSwitchResistorLadder1 voltage to STEP3 i.e., Nominal voltage(2.83),Min vol(2.78),Max(2.89)
  4.Change MasterLightSwitchResistorLadder1 voltage to STEP4 i.e., Nominal voltage(3.58),Min vol(3.51),Max(3.65)
  5.Change MasterLightSwitchResistorLadder1 voltage to previous state i.e.,Nominal voltage (4.26),Min vol(4.17),Max(4.35)
  6.Change MasterLightSwitchResistorLadder1 voltage to
  FAULT_MLS(Open circuit/Short to batt) i.e., Nominal voltage(5),Min vol(4.75),Max(5)
  7.Change MasterLightSwitchResistorLadder1 voltage to FAULT_MLS(Short to gnd) i.e., Nominal voltage(0),Min vol(0),Max(0.75)
  8.Change MasterLightSwitchResistorLadder1 voltage to FAULT_MLS(Out of range) i.e.,
  > 0.75 and < 1.43,
  > 1.49 and < 2.08,
  > 2.16 and < 2.78,
  > 2.89 and < 3.51,
  > 3.65 and < 4.17,
  > 4.35 and < 4.75
- _Pass criteria: 1.MLS position is set to Off_NMastrLghtSwtchPos
  2.MLS position is set to Auto_NMastrLghtSwtchPos
  3.MLS position is set to Side_Lamps_NMastrLghtSwtchPos
  4.MLS position is set to Dipped_Beam_NMastrLghtSwtchPos
  5.MLS position is set to Previous State
  6.MLS position is set to Auto_NMastrLghtSwtchPos
  7.MLS position is set to Auto_NMastrLghtSwtchPos
  8.MLS position is set to Auto_NMastrLghtSwtchPos
- _Regression: No
- _Time [hr]: 0.2
- _Test environment: Lab-Car (auto)

## STC-BDY02-1436: MasterLightSwitchResistorLadder2 voltage
To confirm MasterLightSwitchResistorLadder2 voltage to detect MLS Fog request
- _Object type: Nominal Test
- _Status: REVIEWED
- _Procedure: 1.Change MasterLightSwitchResistorLadder2 voltage to STEP1 i.e., Nominal voltage(3.85),Min vol(3.77),Max(3.93)
  2.Change MasterLightSwitchResistorLadder2 voltage to STEP2 i.e., Nominal voltage(TBD),Min vol(TBD),Max(TBD)
  3.Change MasterLightSwitchResistorLadder2 voltage to STEP3 i.e., Nominal voltage(2.04),Min vol(2),Max(2.08)
  4.Change MasterLightSwitchResistorLadder2 voltage to
  FAULT_MLS(Open circuit/Short to batt) i.e., Nominal voltage(5),Min vol(4.75),Max(5)
  5.Change MasterLightSwitchResistorLadder2 voltage to FAULT_MLS(Short to gnd) i.e., Nominal voltage(0),Min vol(0),Max(0.75)
  6.Change MasterLightSwitchResistorLadder2 voltage to FAULT_MLS(Out of range) i.e.,
  > 0.75 and < 2.0
  > 2.08 and < 3.77
  > 3.93 and < 4.75
- _Pass criteria: 1.MLS fog reuest is set to OFF_BOffOnState(No press)
  2.MLS fog reuest is set to OFF_BOffOnState(Front fog)
  3.MLS fog reuest is set to ON_BOffOnState(Rear fog)
  4.MLS fog reuest is set to OFF_BOffOnState
  5.MLS fog reuest is set to OFF_BOffOnState
  6.MLS fog reuest is set to OFF_BOffOnState
- _Regression: No
- _Time [hr]: 0.25
- _Test environment: Lab-Car (auto)

## STC-BDY02-1437: MLS fault display
To confirm the user display when MLS is faulty
- _Object type: Nominal Test
- _Status: REVIEWED
- _Procedure: 1.Set MLS to faulty state,
  Set MasterLightSwitchResistorLadder1 /MasterLightSwitchResistorLadder2 voltage to
  FAULT_MLS(Open circuit/Short to batt) i.e., Nominal voltage(5),Min vol(4.75),Max(5)
- _Pass criteria: ZB1 shall set 0x01 TBC DTC along with the fault display on DD
- _Regression: No
- _Time [hr]: 0.5
- _Test environment: Lab-Car (auto)

## STC-BDY02-1088: NMasterLightStatus = Dipped beam latched (ID:STC-BDY03-51, STC-HMI01-209)
To confirm master light status as Dipped beam latched when dipped beam is activated
- _Object type: Cross Functional Test
- _Status: REVIEWED
- _Procedure: 1.Set ignition state =5
  2.Activate dipped beam function(i.e.,Position master light switch in 0x2)
  3.Check for NMasterLightStatus Ethernet signal
- _Pass criteria: NMasterLightStatus = 0x2(Dipped_Beam_NMasterLightStatus)
- _Regression: No
- _Time [hr]: 0.3
- _Test environment: Lab-Car (auto)

## STC-BDY02-1087: NMasterLightStatus = Side Lights (ID:STC-HMI01-226)
To confirm master light status as side lights when side light function is activated
- _Object type: Cross Functional Test
- _Status: REVIEWED
- _Procedure: 1.Set ignition state =5
  2.Activate side lights function(i.e.,Position master light switch in 0x1)
  3.Check for NMasterLightStatus Ethernet signal
- _Pass criteria: NMasterLightStatus = 0x1(Side_Lamps_NMasterLightStatus)
- _Regression: No
- _Time [hr]: 0.3
- _Test environment: Lab-Car (auto)

## STC-BDY02-1247: NMasterLightStatus = OFF Lights (ID:STC-ADA02-08-527)
To confirm master light status as OFF light when side light and the Dipped beam are inactive
- _Object type: Cross Functional Test
- _Status: REVIEWED
- _Procedure: 1.Set ignition state =5
  2. Set NSideLightLeftStatus == inactive && NSideLightRightStatus == inactive && NDippedBeamLeftStatus == inactive && NDippedBeamRightStatus == inactive
  3.Check for NMasterLightStatus Ethernet signal
- _Pass criteria: NMasterLightStatus = 0x0 (Off_NMasterLightStatus)
- _Regression: No
- _Time [hr]: 0.3
- _Test environment: Lab-Car (auto)

## STC-BDY02-1096: Dipped beam latch function inactivation with ignition state
To confirm dipped beam latched function inactivation when ignition state <5
- _Object type: Nominal Test
- _Status: REVIEWED
- _Procedure: 1.Activate dipped beam latched function( i.e.,Set NIgnitionStatus == Ignition || Powertrain Activation && Position NMasterLightSwitchPosition = 0x2(Dipped Beam))
  2.Set NIgnitionStatus < 0x5
- _Pass criteria: Dipped Beam Latched Function inactivation.
  NDippedBeamLeftStatus,NDippedBeamRightStatus=Off &&
  NLHDippedBeamLampActiveSts,NRHDippedBeamLampActiveSts=inActive
- _Regression: No
- _Time [hr]: 0.3
- _Test environment: Lab-Car (auto)

## STC-BDY02-1097: Dipped beam latch inactivation with ignition state
To confirm dipped beam latched function inactivation when ignition state = 0x7
- _Object type: Nominal Test
- _Status: REVIEWED
- _Procedure: 1.Activate dipped beam latched function( i.e.,Set NIgnitionStatus == Ignition || Powertrain Activation && Position NMasterLightSwitchPosition = 0x2(Dipped Beam))
  2.Set NIgnitionStatus == Connected Awake 0x7
- _Pass criteria: Dipped Beam Latched Function inactivation.
  NDippedBeamLeftStatus,NDippedBeamRightStatus=Off &&
  NLHDippedBeamLampActiveSts,NRHDippedBeamLampActiveSts=inActive
- _Regression: No
- _Time [hr]: 0.3
- _Test environment: Lab-Car (auto)

## STC-BDY02-1098: Dipped beam latch activation with High severity
To confirm dipped beam latched function activation with high severity
- _Object type: Nominal Test
- _Status: REVIEWED
- _Procedure: 1.Set NIgnitionStatus == 0x2
  2.Set NCrashSeverity=High
- _Pass criteria: Dipped Beam Latched Function Available.
  NDippedBeamLeftStatus,NDippedBeamRightStatus=On_NIlluminationActvStat &&
  NLHDippedBeamLampActiveSts,NRHDippedBeamLampActiveSts=Active_NActivatnSts
- _Regression: No
- _Time [hr]: 0.3
- _Test environment: Lab-Car (auto)

## STC-BDY02-1445: Dipped beam deactivation
Dipped beam fucntion deactivation when MLS = Side light position
- _Object type: Nominal Test
- _Status: REVIEWED
- _Procedure: 1.Activate Dipped beam
  Set ignition state>=5 && Master light switch position is at Dipped,Master Light Switch Position = 2
  2.Deactivate Dipped beam
  Set ignition state>=5 && Master light switch position is at Dipped,Master Light Switch Position = 1
- _Pass criteria: NDippedBeamLeftStatus = Inactive
  NDippedBeamRightStatus = Inactive
- _Regression: No
- _Time [hr]: 0.1
- _Test environment: Lab-Car (auto)

## STC-BDY02-1099: Dipped beam latch activation with Low severity
To confirm dipped beam latched function activation with low severity
- _Object type: Nominal Test
- _Status: REVIEWED
- _Procedure: 1.Set NIgnitionStatus == 0x2
  2.Set NCrashSeverity=Low
- _Pass criteria: Dipped Beam Latched Function Available.
  NDippedBeamLeftStatus,NDippedBeamRightStatus=On_NIlluminationActvStat &&
  NLHDippedBeamLampActiveSts,NRHDippedBeamLampActiveSts=Active_NActivatnSts
- _Regression: No
- _Time [hr]: 0.3
- _Test environment: Lab-Car (auto)

## STC-BDY02-596: Dipped beam while crash
dipped beam illumination when crash occurs
- _Object type: Nominal Test
- _Status: REVIEWED
- _Procedure: 1.Set iNgnition state=5
  2.Simulate NCrashSeverity == High Severity from ORC on Chassis CAN
  3.Simulate NCrashSeverity !== High Severity from ORC on Chassis CAN
- _Pass criteria: 2.Dipped beam lamps shall be illuminated
  3.Dipped beam lamps illumination shall be deactivated
- _Regression: Yes
- _Time [hr]: 0.5
- _Test environment: Lab-Car (auto)

## STC-BDY02-1092: ISO symbol when dipped beam is activated
To confirm ISO symbol when dipped beam is activated
- _Object type: Nominal Test
- _Status: REVIEWED
- _Procedure: 1.Activate dipped beam latched function( i.e.,Set NIgnitionStatus == Ignition || Powertrain Activation && Position NMasterLightSwitchPosition = 0x2(Dipped Beam))
  2.Check ISO symbol
- _Pass criteria: Driver Display dipped beam tell tale illuminated in DDP
- _Regression: No
- _Time [hr]: 0.3
- _Test environment: Lab-Car (manual)

## STC-BDY02-1091: Dipped beam latch function activation
To confirm dipped beam latched function activation with MLS=0x2
- _Object type: Nominal Test
- _Status: REVIEWED
- _Procedure: 1.Set NIgnitionStatus == Ignition || Powertrain Activation
  2.Position NMasterLightSwitchPosition = 0x2(Dipped Beam)
- _Pass criteria: Dipped Beam Latched Function Available.
  NDippedBeamLeftStatus,NDippedBeamRightStatus=On_NIlluminationActvStat &&
  NLHDippedBeamLampActiveSts,NRHDippedBeamLampActiveSts=Active_NActivatnSts
- _Regression: No
- _Time [hr]: 0.3
- _Test environment: Lab-Car (auto)

## STC-BDY02-1105: Rear lights activation with PWM
To confirm rear lights activation when PWM duty cycle is 88%
- _Object type: Nominal Test
- _Status: REVIEWED
- _Procedure: 1.Set NIgnitionState = 0x5
  || PowerTrainStatus = Torque Available
  2.Set PWM duty cycle to 88% using XCp i.e., TailLampsPWM = 88%
- _Pass criteria: NTailLampLeftStatus == Active
  NTailLampRightStatus == Active
  &&
  NLHTailLampActiveSts==Active_NActivatnSts
  NRHTailLampActiveSts==
  Active_NActivatnSts
- _Regression: No
- _Time [hr]: 0.2
- _Test environment: Lab-Car (auto)

## STC-BDY02-1101: Rear lights activation
To confirm rear lights activation when igniton>=2
- _Object type: Nominal Test
- _Status: REVIEWED
- _Procedure: NIgnitionStatus >= Awake (0x2) &&
  NIgnitionStatus != Connected Awake (0x7)
  2.Set Master Light Switch is in the side or dipped lights position
- _Pass criteria: NTailLightLeftStatus = Active
  NTailLightRightStatus = Active
- _Regression: No
- _Time [hr]: 0.2
- _Test environment: Lab-Car (auto)

## STC-BDY02-1107: Rear lamp Short circuit fault
To confirm Rear lights diagnostic strategy when short circuit fault occurs
- _Object type: Nominal Test
- _Status: REVIEWED
- _Procedure: 1.Creat rear lights circuit fault i.e., short circuit fault
  2.After fault, make sure the drive feedback curent is out of normal operation thresholds
- _Pass criteria: 1.NLHRearTailLampActiveSts = TailLampFault
  NRHRearTailLampActiveSts = TailLampFault
  2.A DTC shall be raised
  3.NTailLampClusterMessage = Fault shall be sent to ICU
- _Regression: No
- _Time [hr]: 0.1
- _Test environment: Lab-Car (auto)

## STC-BDY02-1110: Rear lamp Open circuit fault
To confirm Rear lights diagnostic strategy when Open circuit fault occurs
- _Object type: Nominal Test
- _Status: REVIEWED
- _Procedure: 1.Creat rear lights circuit fault i.e., Open circuit fault
  2.After fault, make sure the drive feedback curent is out of normal operation thresholds
- _Pass criteria: 1.NLHRearTailLampActiveSts = TailLampFault
  NRHRearTailLampActiveSts = TailLampFault
  2.A DTC shall be raised
  3.NTailLampClusterMessage = Fault shall be sent to ICU
- _Regression: No
- _Time [hr]: 0.1
- _Test environment: Lab-Car (auto)

## STC-BDY02-1109: Rear lamp circuit circuit fault reset
To confirm Rear lights fault reset with new ignition cycle
- _Object type: Nominal Test
- _Status: REVIEWED
- _Procedure: 1.Creat rear lights circuit fault i.e., Open circuit fault
  2.After fault, make sure the drive feedback curent is out of normal operation thresholds
  3.Start new ignition cycle
- _Pass criteria: NLHRearTailLampActiveSts = TailLampInactive
  NRHRearTailLampActiveSts = RearLampInactive
- _Regression: No
- _Time [hr]: 0.1
- _Test environment: Lab-Car (auto)

## STC-BDY02-1112: Dipped beam activation with Automatic Light
To confirm dipped beam active with automatic light
- _Object type: Nominal Test
- _Status: REVIEWED
- _Procedure: 1.Set NPowertrainStatus == Available
  2.Set
  NMasterLightSwitchPosition == Auto
  3.RLS shall request the dipped beam to be active i.e., NLightSwitchRequest == ON (0x01)
- _Pass criteria: ZB1 shall enable dipped beam activation, BLH_DippedBeamActivate_Req = Active
  BRH_DippedBeamActivate_Req = Active
- _Regression: No
- _Time [hr]: 0.1
- _Test environment: Lab-Car (auto)

## STC-BDY02-1116: Dipped beam deactivation with Automatic Light when MLS is in Side Light or Dipped Beam
To confirm dipped beam deactive with automatic light when MLS is in Side Light or Dipped Beam
- _Object type: Nominal Test
- _Status: REVIEWED
- _Procedure: 1.Activate dipped beam function(Set NPowertrainStatus == Available &&
  NMasterLightSwitchPosition == Auto && NLightSwitchRequest == ON (0x01))
  2. Set MLS is in Side Light or Dipped Beam
- _Pass criteria: ZB1 shall deactivate the dipped beam function , BLH_DippedBeamActivate_Req = Inactive
  BRH_DippedBeamActivate_Req = Inactive
- _Regression: No
- _Time [hr]: 0.1
- _Test environment: Lab-Car (auto)

## STC-BDY02-1115: Dipped beam deactivation with Automatic Light when Powertrain status is unavailable
To confirm dipped beam deactive with automatic light when Powertrain status is unavailable
- _Object type: Nominal Test
- _Status: REVIEWED
- _Procedure: 1.Activate dipped beam function(Set NPowertrainStatus == Available &&
  NMasterLightSwitchPosition == Auto && NLightSwitchRequest == ON (0x01))
  2. Set Powertrain status is unavailable, NPowertrainStatus !== Available
- _Pass criteria: ZB1 shall deactivate the dipped beam function , BLH_DippedBeamActivate_Req = Inactive
  BRH_DippedBeamActivate_Req = Inactive
- _Regression: No
- _Time [hr]: 0.1
- _Test environment: Lab-Car (auto)

## STC-BDY02-1117: Dipped beam deactivation with Automatic Light when Fog light is Active
To confirm dipped beam deactive with automatic light when Fog light is Active
- _Object type: Nominal Test
- _Status: REVIEWED
- _Procedure: 1.Activate dipped beam function(Set NPowertrainStatus == Available &&
  NMasterLightSwitchPosition == Auto && NLightSwitchRequest == ON (0x01))
  2. Activaate Fog light , NFogLightRStatus == Active
- _Pass criteria: ZB1 shall deactivate the dipped beam function , BLH_DippedBeamActivate_Req = Inactive
  BRH_DippedBeamActivate_Req = Inactive
- _Regression: No
- _Time [hr]: 0.1
- _Test environment: Lab-Car (auto)

## STC-BDY02-1114: Dipped beam deactivation with Automatic Light
To confirm dipped beam deactive with automatic light
- _Object type: Nominal Test
- _Status: REVIEWED
- _Procedure: 1.Activate dipped beam function(Set NPowertrainStatus == Available &&
  NMasterLightSwitchPosition == Auto && NLightSwitchRequest == ON (0x01))
  2.Light Switch Request is OFF, NLightSwitchRequest == OFF (0x00)
- _Pass criteria: ZB1 shall deactivate the dipped beam function , BLH_DippedBeamActivate_Req = Inactive
  BRH_DippedBeamActivate_Req = Inactive
- _Regression: No
- _Time [hr]: 0.1
- _Test environment: Lab-Car (auto)

## STC-BDY02-1121: Dipped beam activation with Automatic Light recovers only in next ign cycle
To confirm dipped beam function shall only recover after an ignition cycle with all valid singals
- _Object type: Nominal Test
- _Status: REVIEWED
- _Procedure: 1.Activate dipped beam function(Set NPowertrainStatus == Available &&
  NMasterLightSwitchPosition == Auto && NLightSwitchRequest == ON (0x01))
  2.Light Switch Request is OFF, NLightSwitchRequest == OFF(0x0)
  3.Set NLightSwitchRequest == ON (0x01)
  4.Restart the new ignition cycle
- _Pass criteria: ZB1 shall deactivate the dipped beam function , BLH_DippedBeamActivate_Req = Inactive
  BRH_DippedBeamActivate_Req = Inactive in the current ignition cycle.
  Dipped beam function shall recover only in the new ignition cycle
- _Regression: No
- _Time [hr]: 0.1
- _Test environment: Lab-Car (auto)

## STC-BDY02-1447: RLS Diagnostics
To confirm automatic light functuion when RLS is unavailable
- _Object type: Nominal Test
- _Status: REVIEWED
- _Procedure: 1.Set ignition state >=5
  2.Master Light Switch Position set as AUTO && NPowertrainStatus == Torque Available && (NIgnitionStatus == 0x5 || 0x6) && NFogLightStatus == Inactive && NLightSwitchRequest == Fault (0x02)
- _Pass criteria: NDippedBeamLeftStatus = Active
  NDippedBeamRightStatus = Active
- _Regression: No
- _Time [hr]: 0.1
- _Test environment: Lab-Car (auto)

## STC-BDY02-581: Off light function activation
Off light function activation when IGN>=5
- _Object type: Nominal Test
- _Status: REVIEWED
- _Procedure: 1.Set ignition state =5
  2.Set Master light switch to OFF position from Auto for time period >=MLSOFFPeriod
  3.Set vehicle speed <=4kph
  4.Off light function activation period < LampsOFFTimer
- _Pass criteria: OFF Light Function available.Dipped beam shall be deactivated
- _Regression: Yes
- _Time [hr]: 0.3
- _Test environment: Lab-Car (auto)

## STC-BDY02-590: Off light function activation
Off light function activation when IGN>=5
- _Object type: Nominal Test
- _Status: REVIEWED
- _Procedure: 1.Set ignition state =6(torque available)
  2.Set Master light switch to OFF position from Auto for time period >=MLSOFFPeriod
  3.Set vehicle speed <=4kph
  4.Off light function activation period < LampsOFFTimer
  5.Activate DTRL/Hazard/Main beam/DIMS function while Off light is being actve
- _Pass criteria: OFF Light Function available.Dipped beam shall be deactivated.
  DTRL, Hazards, Main Beam Flash and DIMS functions shall be still available when the OFF Light function is being activated
- _Regression: Yes
- _Time [hr]: 0.3
- _Test environment: Lab-Car (auto)

## STC-BDY02-585: Off light function unavailable
Off light function unavailable when vehicle speed > 4kph
- _Object type: Nominal Test
- _Status: REVIEWED
- _Procedure: 1.Set ignition state >=5
  2.Set Master light switch to OFF position from Auto for time period >=MLSOFFPeriod
  3.Set vehicle speed > 4kph
  4.Off light function activation period < LampsOFFTimer
- _Pass criteria: OFF Light Function Unavailable
- _Regression: No
- _Time [hr]: 0.3
- _Test environment: Lab-Car (auto)

## STC-BDY02-586: Off light function unavailable
Off light function unavailable with master light switch position is set to AUTO
- _Object type: Nominal Test
- _Status: REVIEWED
- _Procedure: 1.Set ignition state >=5
  2.Set Master light switch to OFF for time period >=MLSOFFPeriod
  3.Set vehicle speed <= 4kph
  4.Set MSL=Auto before Off light function activation period < LampsOFFTimer
- _Pass criteria: OFF Light Function available for timeperiod LampsOFFTimer(30sec)
- _Regression: No
- _Time [hr]: 0.3
- _Test environment: Lab-Car (auto)

## STC-BDY02-588: Off light function unavailable
Off light function unavailable with master light switch position is set to side lights
- _Object type: Nominal Test
- _Status: REVIEWED
- _Procedure: 1.Set ignition state >=5
  2.Set Master light switch to OFF for time period >=MLSOFFPeriod
  3.Set vehicle speed <= 4kph
  4.Set MSL=side lights before Off light function activation period < LampsOFFTimer
- _Pass criteria: OFF Light Function Unavailable
- _Regression: No
- _Time [hr]: 0.3
- _Test environment: Lab-Car (auto)

## STC-BDY02-589: Off light function unavailable
Off light function unavailable with master light switch position is set to dipped beam
- _Object type: Nominal Test
- _Status: REVIEWED
- _Procedure: 1.Set ignition state >=5
  2.Set Master light switch to OFF for time period >=MLSOFFPeriod
  3.Set vehicle speed <= 4kph
  4.Set MSL=dipped before Off light function activation period < LampsOFFTimer
- _Pass criteria: OFF Light Function Unavailable
- _Regression: No
- _Time [hr]: 0.3
- _Test environment: Lab-Car (auto)

## STC-BDY02-587: Off light function deactivation
Off light function deactivation after LampsOFFTimer duration
- _Object type: Nominal Test
- _Status: REVIEWED
- _Procedure: 1.Set ignition state >=5
  2.Set Master light switch to OFF position from Auto for time period >=MLSOFFPeriod
  3.Set vehicle speed <= 4kph
  4.Off light function activation period > LampsOFFTimer
- _Pass criteria: OFF Light Function deactivated for after 30sec
- _Regression: No
- _Time [hr]: 0.3
- _Test environment: Lab-Car (auto)

## STC-BDY02-1255: Dipped beam lamps status failure
To confirm ZB1 shall raise DTC when dipped beam lamp status failure
- _Object type: Nominal Test
- _Status: REVIEWED
- _Procedure: 1.Set NIgnitionStatus >= 0x05
  2.ZA1 receiver dipped beam lamps status failure signal from HeadLamp LIN, HeadLampsLIN::BStat_L_Failed == Failed ||
  HeadLampsLIN::BStat_R_Failed == Failed
- _Pass criteria: ZA1 shall Raise DTC,
  NLHDippedBeamLampActiveSts = Fault ||
  NRHDippedBeamLampActiveSts = Fault
- _Regression: No
- _Time [hr]: 0.1
- _Test environment: Lab-Car (auto)

## STC-BDY02-1448: Dipped beam lamps status failure error recovery
To confirm DTC Shall clear when dipped beam lamp status failure error has cleared
- _Object type: Nominal Test
- _Status: REVIEWED
- _Procedure: 1.Set NIgnitionStatus >= 0x05
  2.Activate Dipped beam lamp status error:
  HeadLampsLIN::BStat_L_Failed == Failed ||
  HeadLampsLIN::BStat_R_Failed == Failed
  3.Recover dipped beam status error:
  Send valid LIN message for 10 consecutive frames,
  HeadLampsLIN::BStat_L_Failed == OK ||
  HeadLampsLIN::BStat_R_Failed == OK
- _Pass criteria: ZA1 shall clear DTC,
  NLHDippedBeamLampActiveSts = OK ||
  NRHDippedBeamLampActiveSts = OK
- _Regression: No
- _Time [hr]: 0.1
- _Test environment: Lab-Car (auto)

## STC-BDY02-1449: Dipped Beam lamp Communications Failure
To confirm ZB1 Shall raise DTC when Dipped beam lamps communication failed
- _Object type: Nominal Test
- _Status: REVIEWED
- _Procedure: 1.Set NIgnitionStatus >= 0x05
  2.ZA1 receive Dipped beam lamps communication failure on HeadLamp LIN,
  HeadLampsLIN::BCOM_L_Failed == Failed ||
  HeadLampsLIN::BCOM_R_Failed == Failed
- _Pass criteria: ZA1 Shall Raise DTC
  NLHDippedBeamLampActiveSts = Fault ||
  NRHDippedBeamLampActiveSts = Fault
- _Regression: No
- _Time [hr]: 0.1
- _Test environment: Lab-Car (auto)

## STC-BDY02-1450: Dipped Beam lamp Communications Failure error recovery
To confirm DTC Shall clear when Dipped beam lamps communication failed error has cleared
- _Object type: Nominal Test
- _Status: REVIEWED
- _Procedure: 1.Set NIgnitionStatus >= 0x05
  2.Activate Dipped beam Communications Failure:
  HeadLampsLIN::BCOM_L_Failed == Failed ||
  HeadLampsLIN::BCOM_R_Failed == Failed
  3.Recover dipped beam Communications Failure:
  Send valid LIN message for 10 consecutive frames,
  HeadLampsLIN::BCOM_L_Failed == OK ||
  HeadLampsLIN::BCOM_R_Failed == OK
- _Pass criteria: NLHDippedBeamLampActiveSts = OK ||
  NRHDippedBeamLampActiveSts = OK
- _Regression: No
- _Time [hr]: 0.1
- _Test environment: Lab-Car (auto)

## STC-BDY02-1451: Dipped beam Thermal failure or FAN in the Lamp failure
To confirm ZB1 shall set DTC when Dipped beam Thermal failure or FAN in the Lamp failure
- _Object type: Nominal Test
- _Status: REVIEWED
- _Procedure: 1.Set NIgnitionStatus >= 0x05
  2.ZB1 receive Dipped beam Thermal failure or FAN in the Lamp failure on HeadLamp LIN,
  HeadLampsLIN::BFAN_L_Failed == Failed ||
  HeadLampsLIN::BFAN_R_Failed == Failed
- _Pass criteria: ZA1 shall Raise DTC
  NLHDippedBeamLampActiveSts = Fault ||
  NRHDippedBeamLampActiveSts = Fault
- _Regression: No
- _Time [hr]: 0.1
- _Test environment: Lab-Car (auto)

## STC-BDY02-1452: Dipped beam Thermal failure or FAN in the Lamp failure error recovery
To confirm DTC Shall clear Dipped beam Thermal failure or FAN in the Lamp failure error has cleared
- _Object type: Nominal Test
- _Status: REVIEWED
- _Procedure: 1.Set NIgnitionStatus >= 0x05
  2.Activate Dipped beam Thermal failure or FAN in the Lamp failure:
  HeadLampsLIN::BFAN_L_Failed == Failed ||
  HeadLampsLIN::BFAN_R_Failed == Failed
  3.Recover Dipped beam Thermal failure or FAN in the Lamp failure:
  Send valid LIN message for 10 consecutive frames,
  HeadLampsLIN::BFAN_L_Failed == OK ||
  HeadLampsLIN::BFAN_R_Failed == OK
- _Pass criteria: NLHDippedBeamLampActiveSts = OK ||
  NRHDippedBeamLampActiveSts = OK
- _Regression: No
- _Time [hr]: 0.1
- _Test environment: Lab-Car (auto)

## STC-BDY02-1453: Dipped Beam lamp Response Error
To confirm ZB1 shall raise DTC when Dipped Beam lamp Response Error
- _Object type: Nominal Test
- _Status: REVIEWED
- _Procedure: 1.Set NIgnitionStatus >= 0x05
  2.ZB1 receive Dipped Beam lamp Response Error
  on HeadLamp LIN,
  HeadLampsLIN::BBLRResponseError == Error ||
  HeadLampsLIN::BBLLResponseError== Error
- _Pass criteria: ZA1 shall Raise DTC
  NLHDippedBeamLampActiveSts = Fault ||
  NRHDippedBeamLampActiveSts = Fault
- _Regression: No
- _Time [hr]: 0.1
- _Test environment: Lab-Car (auto)

## STC-BDY02-1454: Dipped Beam lamp Response Error recovery
To confirm ZB1 shall clear DTC Dipped Beam lamp Response Error has cleared
- _Object type: Nominal Test
- _Status: REVIEWED
- _Procedure: 1.Set NIgnitionStatus >= 0x05
  2.Activate Dipped Beam lamp Response Error:
  HeadLampsLIN::BBLRResponseError == Error ||
  HeadLampsLIN::BBLLResponseError== Error
  3.Recover Dipped Beam lamp Response Error:
  Send valid LIN message for 10 consecutive frames,
  HeadLampsLIN::BBLRResponseError == No Error ||
  HeadLampsLIN::BBLLResponseError== No Error
- _Pass criteria: NLHDippedBeamLampActiveSts = OK ||
  NRHDippedBeamLampActiveSts = OK
- _Regression: No
- _Time [hr]: 0.1
- _Test environment: Lab-Car (auto)

## STC-BDY02-1455: Dipped Beam Power Supply of the lamp is Too Low
To confirm ZB1 shall raise DTC Dipped Beam Power Supply of the lamp is Too Low
- _Object type: Nominal Test
- _Status: REVIEWED
- _Procedure: 1.Set NIgnitionStatus >= 0x05
  2.ZB1 receive Dipped Beam Power Supply of the lamp is Too Low on HeadLamp LIN,
  HeadLampsLIN::BPowerSupply_L == Too Low ||
  HeadLampsLIN::BPowerSupply_R== Too Low
- _Pass criteria: ZA1 shall Raise DTC
  NLHDippedBeamLampActiveSts = Fault ||
  NRHDippedBeamLampActiveSts = Fault
- _Regression: No
- _Time [hr]: 0.1
- _Test environment: Lab-Car (auto)

## STC-BDY02-1456: Dipped Beam Power Supply of the lamp is Too Low Error recovery
To confirm ZB1 shall clear DTCDipped Beam Power Supply of the lamp is Too Low Error recovery
- _Object type: Nominal Test
- _Status: REVIEWED
- _Procedure: 1.Set NIgnitionStatus >= 0x05
  2.Dipped Beam Power Supply of the lamp is Too Low Error:
  HeadLampsLIN::BPowerSupply_L == Too Low ||
  HeadLampsLIN::BPowerSupply_R== Too Low
  3.Recover Dipped Beam Power Supply of the lamp is Too Low Error:
  Send valid LIN message for 10 consecutive frames,
  HeadLampsLIN::BPowerSupply_L == OK ||
  HeadLampsLIN::BPowerSupply_R== Ok
- _Pass criteria: NLHDippedBeamLampActiveSts = OK ||
  NRHDippedBeamLampActiveSts = OK
- _Regression: No
- _Time [hr]: 0.1
- _Test environment: Lab-Car (auto)

## STC-BDY02-1457: Dipped Beam open/short circuit failure
To confirm ZB1 shall raise DTC when Dipped Beam open/short circuit failure
- _Object type: Nominal Test
- _Status: REVIEWED
- _Procedure: 1.Set NIgnitionStatus >= 0x05
  2.Create Open/Short ciruit failure of the Dipped beam lamps
- _Pass criteria: ZB1 shall Raise DTC
  NLHDippedBeamLampActiveSts = Fault
  NRHDippedBeamLampActiveSts = Fault && NDippedBeamClusterMessage = Fault display on ICU
- _Regression: No
- _Time [hr]: 0.1
- _Test environment: Lab-Car (auto)

## STC-BDY02-1458: Dipped Beam open/short circuit failure recovery
To confirm ZB1 shall clear DTC when Dipped Beam open/short circuit failure Error recovery
- _Object type: Nominal Test
- _Status: REVIEWED
- _Procedure: 1.Set NIgnitionStatus >= 0x05
  2.Create Open/Short ciruit failure of the Dipped beam lamps, Drive feedback current out of normal operation range for debounce time
  3.Clear the fault:
  Drive feedback current within normal operation range for debounce time ||
  A new ignition cycle
- _Pass criteria: NLHDippedBeamLampActiveSts = Inactive
  NRHDippedBeamLampActiveSts = Inactive && NDippedBeamClusterMessage = Fault display shall be cleared on ICU
- _Regression: No
- _Time [hr]: 0.1
- _Test environment: Lab-Car (auto)

## STC-BDY02-1123: Side light function activation
To confirm side light function activation in ignition state =0x05
- _Object type: Nominal Test
- _Status: REVIEWED
- _Procedure: 1.Set NIgnitionStatus = 0x05
  2.NMasterLightSwitchPosition == Side Light || Dipped Beam
- _Pass criteria: NSideLightLeftStatus = Active NSideLightRightStatus = Active
- _Regression: No
- _Time [hr]: 0.1
- _Test environment: Lab-Car (auto)

## STC-BDY02-1124: Side light function activation with AUTO function
To confirm side light function activation with AUTO light activation
- _Object type: Nominal Test
- _Status: REVIEWED
- _Procedure: 1.Set NIgnitionStatus = 0x05 ||
  PowertrainStatus = Torque Available
  2.NMasterLightSwitchPosition == AUTO
- _Pass criteria: NSideLightLeftStatus = Active NSideLightRightStatus = Active
- _Regression: No
- _Time [hr]: 0.1
- _Test environment: Lab-Car (auto)

## STC-BDY02-1125: Side light function activation with dipped beam activation
To confirm side light function activation with dipped beam activation
- _Object type: Nominal Test
- _Status: REVIEWED
- _Procedure: NMasterLightSwitchPosition == OFF || AUTO
  && (NDippedBeamLeftStatus = Active NDippedBeamRightStatus = Active)
- _Pass criteria: NSideLightLeftStatus = Active NSideLightRightStatus = Active
- _Regression: No
- _Time [hr]: 0.1
- _Test environment: Lab-Car (auto)

## STC-BDY02-1126: Side light function deactivation with ignition state
To confirm side light function deactivation when ignition state !=0x05 || Powertrain Activation
- _Object type: Nominal Test
- _Status: REVIEWED
- _Procedure: 1.Set NIgnitionStatus = 0x05
  2.NMasterLightSwitchPosition == Side Light || Dipped Beam
  3.Set NIgnitionStatus !=0x05 || Powertrain Activation
- _Pass criteria: NSideLightLeftStatus = InActive NSideLightRightStatus = InActive
- _Regression: No
- _Time [hr]: 0.1
- _Test environment: Lab-Car (auto)

## STC-BDY02-1127: side & tail lamps illumination when side lights are activated
To confirm side & tail lamps illumination when side lights are activated
- _Object type: Nominal Test
- _Status: REVIEWED
- _Procedure: Activate side light function(Set NIgnitionStatus = 0x05
  && NMasterLightSwitchPosition == Side Light || Dipped Beam)
- _Pass criteria: BLH_SidelampPositionIndicator = Active
  BRH_SidelampPositionIndicator = Active
  NTailLightLeftStatus = Active
  NTailLightRightStatus = Active
- _Regression: No
- _Time [hr]: 0.1
- _Test environment: Lab-Car (auto)

## STC-BDY02-1128: ISO symbol when side lights function is activated
To confirm ISO symbol when side lights function is activated
- _Object type: Nominal Test
- _Status: REVIEWED
- _Procedure: 1.Activate side light function(Set NIgnitionStatus = 0x05
  && NMasterLightSwitchPosition == Side Light || Dipped Beam)
  2.Check ISO symbol
- _Pass criteria: Driver Display side lights tell tale illuminated in DDP
- _Regression: No
- _Time [hr]: 0.3
- _Test environment: Lab-Car (manual)

## STC-BDY02-228: Side Light control logic- Hazard ON
Side light function shall be deactivated when hazard is active
- _Object type: Nominal Test
- _Status: REVIEWED
- _Procedure: 1.NHazardStatus = 0x0 && NIndicatorLStatus =0x0 && NIndicatorRStatus = 0x0
  2.Set ignition status ≥ 5 && Master Light Switch Position = 1 || 2
  3.Set NHazardStatus= 0x1
  4.Set NHazardStatus= 0x0
- _Pass criteria: 2.Side lights active.
  NSideLightLeftStatus = (0x1) && NSideLightRightStatus = (0x1),
  NTailLightLeftStatus = (0x1) && NTailLightRightStatus = (0x1),
  NMasterLightStatus = (0x1)
  3.Side lights inactive.
  NSideLightLeftStatus = (0x0) && NSideLightRightStatus = (0x0),
  NMasterLightStatus = (0x1)
  NTailLightLeftStatus = (0x1) && NTailLightRightStatus = (0x1)
  4.Side lights active.
  NSideLightLeftStatus = (0x1) && NSideLightRightStatus = (0x1)
- _Regression: Yes
- _Time [hr]: 0.4
- _Test environment: Lab-Car (auto)

## STC-BDY02-1131: Side light Short circuit fault
To confirm Rear lights diagnostic strategy when short circuit fault occurs
- _Object type: Nominal Test
- _Status: REVIEWED
- _Procedure: 1.Creat Side light circuit fault i.e., short circuit fault
  2.After fault, make sure the drive feedback curent is out of normal operation thresholds
- _Pass criteria: NLHFrontLampActiveSts = SideLampInactive
  NRHFrontLampActiveSts = SideLampInactive
  2.A DTC shall be raised
  3.NSideLightClusterMessage = Fault
- _Regression: No
- _Time [hr]: 0.1
- _Test environment: Lab-Car (auto)

## STC-BDY02-1132: Side light open circuit fault
To confirm Rear lights diagnostic strategy when open circuit fault occurs
- _Object type: Nominal Test
- _Status: REVIEWED
- _Procedure: 1.Creat Side light circuit fault i.e., open circuit fault
  2.After fault, make sure the drive feedback curent is out of normal operation thresholds
- _Pass criteria: NLHFrontLampActiveSts = SideLampInactive
  NRHFrontLampActiveSts = SideLampInactive
  2.A DTC shall be raised
  3.NSideLightClusterMessage = Fault
- _Regression: No
- _Time [hr]: 0.1
- _Test environment: Lab-Car (auto)

## STC-BDY02-1133: Side light circuit circuit fault reset
To confirm Rear lights fault reset with new ignition cycle
- _Object type: Nominal Test
- _Status: REVIEWED
- _Procedure: 1.Creat Side light circuit fault i.e., Open circuit fault
  2.After fault, make sure the drive feedback curent is out of normal operation thresholds
  3.Start new ignition cycle
- _Pass criteria: NLHFrontLampActiveSts = SideLampInactive
  NRHFrontLampActiveSts = SideLampInactive
- _Regression: No
- _Time [hr]: 0.1
- _Test environment: Lab-Car (auto)

## STC-BDY02-1628: Approach Light Function Activation
The Approach Event shall be activated when the vehicle gets unlocked and the entry lighting is enabled and the battery state of charge is not low.
- _Object type: Nominal Test
- _Status: REVIEWED
- _Procedure: Preconditions:
  NTEntryLighting != OFF &&
  NBatteryLowStateOfCharge == OK
  1. Vehicle Unlocked
  NVehicleLockStatus [PE Lock] or [RKE Lock] -
  2. Vehicle locked
  NVehicleLockStatus [PE Unlock] or [RKE Unlock]
- _Pass criteria: 2. BApproachLightStatus = ON(0x1)
  NDippedBeamLeftStatus = ON
  NDippedBeamRightStatus = ON
  NSideLightLeftStatus = ON
  NSideLightRightStatus = ON
  NTailLightLeftStatus = ON
  NTailLightRightStatus = ON
- _Regression: No
- _Time [hr]: 0.2
- _Test environment: Lab-Car (manual)

## STC-BDY02-1629: TApproachLightTimer
The approach lighting function shall de-activated when RKE or PE Lock is detected or calibratable timer (TApproachLightTimer) expires.
- _Object type: Nominal Test
- _Status: REVIEWED
- _Procedure: BApproachLightStatus = ON &&
  NVehicleLockStatus == [PE Lock] or [RKE Lock]
  or
  Approach Light Function being activated for over than TApproachLightTimer
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1630: Approach Light Function Deactivation (ignition status)
The Approach Event shall be deactivated when Ignition State is greater than Ignition (0x5).
- _Object type: Nominal Test
- _Status: REVIEWED
- _Procedure: BApproachLightStatus = ON &&
  NIgnitionStatus > 0x5
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1631: Approach Light Function Deactivation (battery status)
The Approach Event shall be deactivated when the battery state of charge is low.
- _Object type: Nominal Test
- _Status: REVIEWED
- _Procedure: Preconditions:
  BApproachLightStatus = ON &&
  NBatteryLowStateOfCharge != OK
  Test:
  1. Lock the vehicle
- _Pass criteria: Verify that:
  BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1632: Approach Light Function Deactivation (entry light disabled)
The Approach Event shall be deactivated when the entry lighting is disabled on central display.
- _Object type: Nominal Test
- _Status: REVIEWED
- _Procedure: Preconditions:
  BApproachLightStatus = ON &&
  NTEntryLighting == OFF
  Test:
  1. Lock the vehicle
- _Pass criteria: Verify that:
  BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1633: Approach Light Function Deactivation (entry lighting timer)
The Approach Event shall be deactivated when the entry lighting timer is reached.
- _Object type: Nominal Test
- _Status: REVIEWED
- _Procedure: BApproachLightStatus = ON &&
  NTEntryLighting timer reached
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1634: Approach Light Function Deactivation (ADI comm fault)
The Approach Event shall be deactivated when ADI communication is in fault
- _Object type: Nominal Test
- _Status: REVIEWED
- _Procedure: BApproachLightStatus = ON &&
  ADI communication fault raised
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.2
- _Test environment: Lab-Car (manual)

## STC-BDY02-1461: Approach Light timer user config (ID: STC-CFG02-01-1150)
To confirm Approach Light timer user config
- _Object type: Cross Functional Test
- _Status: REVIEWED
- _Procedure: 1.Activate approach light function:
  NIgnitionStatus <= Awake &&
  NVehicleLockStatus == RKE Unlock
  2.Set TApproachLightTimer to different values using UserConfig settings from ADI:
  Reference SDS-CFG02-01-308
- _Pass criteria: TApproachLightTimer: set to >10secs
  0x0 = OFF
  0x1 = 10 Seconds
  0x2 = 15 Seconds
  0x3 = 20 Seconds
  0x4 = 30 Seconds
  0x5 = 40 Seconds
  0x6 = 50 Seconds
  0x7 = 60 Seconds
- _Regression: No
- _Time [hr]: 0.2
- _Test environment: Lab-Car (auto)

## STC-BDY02-375: Approach light user settings (ID:STC-CFG02-01-1150, STC-CFG02-01-1151, STC-CFG02-01-1152)
Approach light user settings using menu stalk and lighting timer
- _Object type: Cross Functional Test
- _Status: REVIEWED
- _Procedure: Set approach lighting timer as per below:
  NTEntryLighting Timer (
  )_x000D_
  f (0
  1 15
  30_x000D_3 45_x000D_4
  NMenuLStalkBackStatus, _x000D_NMenuLStalkForwardStatus
  NMenuLStalkDownStatus,_x000D_NMenuLStalkUpStatus
- _Pass criteria: NDippedBeamLeftStatus && NDippedBeamRightStatus shall follow the approach light timer and shall deactivate when timer expires
- _Regression: Yes
- _Time [hr]: 0.5
- _Test environment: Lab-Car (manual)

## STC-BDY02-1635: Approach Event lighting function timer configuration
The Approach Event lighting function timer shall be able to be configured by the user via Menu Stalk or contact screen
- _Object type: Nominal Test
- _Status: REVIEWED
- _Procedure: Check the central display and chenge the entry light time configuraion
- _Pass criteria: NTEntryLighting value changes according to the central display settings
- _Regression: No
- _Time [hr]: 0.1
- _Test environment: Lab-Car (manual)

## STC-BDY02-475: See You Home activation
- _Object type: Nominal Test
- _Status: REVIEWED
- _Procedure:
  1. Set Ignition State = 2
  2. Lock the car using RKE keys
- _Pass criteria:
  1. BSeeYouHomeStatus = ON
  & Dipped Beam ON,
  NDippedBeamLeftStatus = (0x1) && NDippedBeamRightStatus = (0x1)
- _Regression: Yes
- _Time [hr]: 0.5
- _Test environment: Lab-Car (auto)

## STC-BDY02-539: See You Home Activation
See You Home Activation when Left door transition to Open and timer > 0
- _Object type: Nominal Test
- _Status: REVIEWED
- _Procedure: 1.Set NIgnitionStatus=2
  2.Set Timer Signal different from "OFF", NSeeYouHomeTimer >0 ||
  NTExitLighting >0
  3.VehicleLock Status == RKE Locked || PE Locked
- _Pass criteria: BSeeYouHomeStatus = ON
- _Regression: Yes
- _Time [hr]: 0.4
- _Test environment: Lab-Car (auto)

## STC-BDY02-548: See You Home Activation
See You Home Activation when Right door transition to Open and timer > 0
- _Object type: Nominal Test
- _Status: REVIEWED
- _Procedure: 1.Set NIgnitionStatus=2
  2.Set Timer Signal different from "OFF", NSeeYouHomeTimer >0 ||
  NTExitLighting >0
  3.VehicleLock Status == RKE Locked || PE Locked
- _Pass criteria: BSeeYouHomeStatus = ON
- _Regression: Yes
- _Time [hr]: 0.4
- _Test environment: Lab-Car (auto)

## STC-BDY02-549: See You Home deactivation with Right door open when timer=0
See You Home deactivation when Right door transition to Open and timer = OFF
- _Object type: Negative Test
- _Status: REVIEWED
- _Procedure: 1.Set NIgnitionStatus=2
  2.Set Timer Signal to "OFF", NSeeYouHomeTimer = 0 ||
  NTExitLighting = 0
  3.Right door transitions to an Open status, NDoorROpenStatus = 1
- _Pass criteria: CUHomeActive= False and Dipped Beam=OFF
- _Regression: No
- _Time [hr]: 0.4
- _Test environment: Lab-Car (auto)

## STC-BDY02-550: See You Home deactivation with Left door open when timer=0
See You Home deactivation when Left door transition to Open and timer = OFF
- _Object type: Negative Test
- _Status: REVIEWED
- _Procedure: 1.Set NIgnitionStatus=2
  2.Set Timer Signal to "OFF", NSeeYouHomeTimer = 0 ||
  NTExitLighting = 0
  3.Left door transitions to an Open status, NDoorLOpenStatus = 1
- _Pass criteria: CUHomeActive= False and Dipped Beam=OFF
- _Regression: No
- _Time [hr]: 0.4
- _Test environment: Lab-Car (auto)

## STC-BDY02-551: See You Home deactivation with ignition state transition to 1
See You Home deactivation when ignition state transition to 1 from 2 while CUHome is Active
- _Object type: Nominal Test
- _Status: REVIEWED
- _Procedure: 1.Activate See You Home:
  NIgnitionStatus == Awake &&
  (VehicleLock Status == RKE Locked || PE Locked) &&
  TSeeYouHomeTimer > 0
  2.Do Igniton state transition from 2 to 1, NIgnitionStatus = 1 within timer expires
- _Pass criteria: 1.CUHomeActive= True and Dipped Beam=ON
  2.CUHomeActive= False and Dipped Beam=OFF
- _Regression: No
- _Time [hr]: 0.3
- _Test environment: Lab-Car (auto)

## STC-BDY02-552: See You Home deactivation with ignition state transition >2
See You Home deactivation when ignition state transition >2 while CUHome is Active
- _Object type: Nominal Test
- _Status: REVIEWED
- _Procedure: 1.Activate See You Home:
  NIgnitionStatus == Awake &&
  (VehicleLock Status == RKE Locked || PE Locked) &&
  TSeeYouHomeTimer > 0
  2.Set NIgnitionStatus > 2 within timer expiration
- _Pass criteria: 1.CUHomeActive= True and Dipped Beam=ON
  2.CUHomeActive= False and Dipped Beam=OFF
- _Regression: No
- _Time [hr]: 0.3
- _Test environment: Lab-Car (auto)

## STC-BDY02-553
See You Home deactivation when Car is locked then unlocked again while CUHome is Active
- _Object type: Nominal Test
- _Status: REVIEWED
- _Procedure: 1.Activate See You Home:
  NIgnitionStatus == Awake &&
  (VehicleLock Status == RKE Locked || PE Locked) &&
  TSeeYouHomeTimer > 0
  2.Lock the vehicle and then unlock again within timer expiration
- _Pass criteria: 1.CUHomeActive= True and Dipped Beam=ON
  2.CUHomeActive= False and Dipped Beam=OFF
- _Regression: No
- _Time [hr]: 0.3
- _Test environment: Lab-Car (auto)

## STC-BDY02-554
See You Home deactivation when Car is locked and the Timer expired while CUHome is Active
- _Object type: Nominal Test
- _Status: REVIEWED
- _Procedure: 1.Activate See You Home:
  NIgnitionStatus == Awake &&
  (VehicleLock Status == RKE Locked || PE Locked) &&
  TSeeYouHomeTimer > 0
  2.Lock the vehicle and wait till timer expires
- _Pass criteria: 1.CUHomeActive= True and Dipped Beam=ON
  2.CUHomeActive= False and Dipped Beam=OFF
- _Regression: No
- _Time [hr]: 0.3
- _Test environment: Lab-Car (auto)

## STC-BDY02-1463
See You Home deactivation when vehicle is unlocked(RKE Unlock or PE Unlock) before timeout
- _Object type: Nominal Test
- _Status: REVIEWED
- _Procedure: 1.Activate See You Home:
  NIgnitionStatus == Awake &&
  (VehicleLock Status == RKE Locked || PE Locked) &&
  TSeeYouHomeTimer > 0
  2.Lock the vehicle, NVehicleLockStatus == RKE Unlock || PE Unlock
- _Pass criteria: BSeeYouHomeStatus = OFF (0x0)
- _Regression: No
- _Time [hr]: 0.1
- _Test environment: Lab-Car (auto)

## STC-BDY02-1464: See You Home deactivation when calibratable timer expires
- _Object type: Nominal Test
- _Status: REVIEWED
- _Procedure: 1.Activate See You Home:
  NIgnitionStatus == Awake &&
  (VehicleLock Status == RKE Locked || PE Locked) &&
  TSeeYouHomeTimer > 0
  2.Wait until the calibration timer expires, TSeeYouHomeTimer == 0
- _Pass criteria: BSeeYouHomeStatus = OFF (0x0)
- _Regression: No
- _Time [hr]: 0.2
- _Test environment: Lab-Car (auto)

## STC-BDY02-555: See You Home Temporarily Time
See You Home Temporarily time activation
- _Object type: Nominal Test
- _Status: REVIEWED
- _Procedure: 1.Set NIgnitionStatus = 2
  2.Pull DI Stalk towards the user, NFlashMainSwitch= 0x1
  3.Lock the vehicle using RKE lock button, NVehicleLockStatus = 0x5
  4.Set See You Home Temporarily Time not equal to OFF,
  NSeeYouHomeTimer !=0
- _Pass criteria: See You Home Lighting shall be activated for See You Home Temporarily Time.
  CUHomeTimer = NSeeYouHomeTimer
  See You Home Fixed
  e_x000D_See You Home Temporarily Time Timer (se
  )_x000D_
  f (0
  1 15
  30_x000D_3 45
- _Regression: No
- _Time [hr]: 0.3
- _Test environment: Lab-Car (auto)

## STC-BDY02-556: See You Home Temporarily Time
See You Home Temporarily time activation
- _Object type: Nominal Test
- _Status: REVIEWED
- _Procedure: 1.Set NIgnitionStatus = 2
  2.Pull DI Stalk towards the user, NFlashMainSwitch= 0x1
  3.Lock the vehicle using PE lock button, (NVehicleLockStatus == RKE Lock || PE Lock)
  4.Set See You Home Temporarily Time not equal to OFF, NSeeYouHomeTimer >0 || NTExitLighting >0
- _Pass criteria: See You Home Lighting shall be activated for See You Home Temporarily Time.
  CUHomeTimer = NSeeYouHomeTimer
  See You Home Fixed
  e_x000D_See You Home Temporarily Time Timer (se
  )_x000D_
  f (0
  1 15
  30_x000D_3 45
- _Regression: Yes
- _Time [hr]: 0.3
- _Test environment: Lab-Car (auto)

## STC-BDY02-558
See You Home Temporarily Time shall take precedence over the See You Home Fixed Time when NSeeYouHomeTimer !=0
- _Object type: Nominal Test
- _Status: REVIEWED
- _Procedure: 1.Set NIgnitionStatus = 2
  2.Set See You Home Temporarily Time not equal to OFF,
  NSeeYouHomeTimer !=0 (NTExitLighting !=0)
  3.Lock the vehicle (RKE or PE lock (NVehicleLockStatus = 0x5 || 0x6)
  4.Pull the DI Stalk, NFlashMainSwitch= 0x1 before timer expires
- _Pass criteria: 3. TSeeYouHomeTimer = CUHomeTempTime
  4. See You Home Lighting function activated
- _Regression: Yes
- _Time [hr]: 0.4
- _Test environment: Lab-Car (auto)

## STC-BDY02-477: See You Home Lighting timer
See You Home Lighting timer user configuration
- _Object type: Nominal Test
- _Status: REVIEWED
- _Procedure:
  1. Configure See You Home Lighting timer through the Menu on the driver display using the Menu stalk [ UserConfig::NTExitLighting]
  NTExitLighting Timer (
  )_x000D_
  f (0
  1 15
  30_x000D_3 45
- _Pass criteria: See you home lighting i.e., Dipped beam ON duration shall follow the NSeeYouHomeTimer
- _Regression: No
- _Time [hr]: 0.5
- _Test environment: Lab-Car (auto)

## STC-BDY02-1465: See You Home Temporarily Time increment
See You Home Temporarily Time increment using DIMS stalk
- _Object type: Nominal Test
- _Status: REVIEWED
- _Procedure: 1.NIgnitionStatus == Awake
  2.Pull DIMS stalk towards the steering wheel to a momentary position - first time
  3.Pull DIMS stalk towards the steering wheel to a momentary position - second time
  4.Pull DIMS stalk towards the steering wheel to a momentary position - more than three times
- _Pass criteria: Default:
  CUHomeTempTime = 15 Seconds
  Pull Flash first time:
  CUHomeTempTime = 30 Seconds
  Pull Flash second time:
  CUHomeTempTime = 45 Seconds
  Pull Flash more than three times:
  CUHomeTempTime = 60 Seconds
- _Regression: No
- _Time [hr]: 0.1
- _Test environment: Lab-Car (auto)

## STC-BDY02-1611: Welcome Event activation
Welcome event activation when the vehicle is locked, the passive entry is enable, the keyfob is detected to enter Welcome Zone, the entry lighting is enabled and the battery state of charge is not low
- _Object type: Nominal Test
- _Status: REVIEWED
- _Procedure: BWelcomeEventActive == ON &&
  NTEntryLighting != OFF &&
  NignitionState == LOCKED &&
  NBatteryLowStateOfCharge == OK
- _Pass criteria: BWelcomeEventStatus = ON
  NSideLightLeftStatus = ON
  NSideLightRightStatus = ON
  NTailLightLeftStatus = ON
  NTailLightRightStatus = ON
- _Regression: No
- _Time [hr]: 0.4
- _Test environment: Lab-Car (auto)

## STC-BDY02-1612: Welcome Event deactivation
Welcome event deactivation when Ignition State is greater than Awake (0x2)
- _Object type: Nominal Test
- _Status: REVIEWED
- _Procedure: BWelcomeEventStatus == ON &&
  NignitionState >= Awake
- _Pass criteria: BWelcomeEventStatus = OFF
  NSideLightLeftStatus = OFF
  NSideLightRightStatus = OFF
  NTailLightLeftStatus = OFF
  NTailLightRightStatus = OFF
- _Regression: No
- _Time [hr]: 0.4
- _Test environment: Lab-Car (auto)

## STC-BDY02-1613: Welcome Event deactivation
Welcome event deactivation when the battery state of charge is low
- _Object type: Nominal Test
- _Status: REVIEWED
- _Procedure: BWelcomeEventStatus == ON &&
  NBatteryLowStateOfCharge != OK
- _Pass criteria: BWelcomeEventStatus = OFF
  NSideLightLeftStatus = OFF
  NSideLightRightStatus = OFF
  NTailLightLeftStatus = OFF
  NTailLightRightStatus = OFF
- _Regression: No
- _Time [hr]: 0.4
- _Test environment: Lab-Car (auto)

## STC-BDY02-1614: Welcome Event deactivation
Welcome Event deactivation when the keyfob is detected to exit Welcome Zone or to stay in Welcome Zone over a timeout
- _Object type: Nominal Test
- _Status: REVIEWED
- _Procedure: BWelcomeEventStatus == ON &&
  BWelcomeEventActive == OFF
- _Pass criteria: BWelcomeEventStatus = OFF
  NSideLightLeftStatus = OFF
  NSideLightRightStatus = OFF
  NTailLightLeftStatus = OFF
  NTailLightRightStatus = OFF
- _Regression: No
- _Time [hr]: 0.4
- _Test environment: Lab-Car (auto)

## STC-BDY02-1615: Welcome Event deactivation
Welcome Event deactivation when ADI communication is in fault
- _Object type: Nominal Test
- _Status: REVIEWED
- _Procedure: BWelcomeEventStatus == ON &&
  ADI communication fault raised
- _Pass criteria: BWelcomeEventStatus = OFF
  NSideLightLeftStatus = OFF
  NSideLightRightStatus = OFF
  NTailLightLeftStatus = OFF
  NTailLightRightStatus = OFF
- _Regression: No
- _Time [hr]: 0.4
- _Test environment: Lab-Car (manual)

## STC-BDY02-1616: Sign Off Event activation
Sign Off Event activation when the door gets open after Ignition State drops to Awake, the exit lighting is enabled and the battery state of charge is not low
- _Object type: Nominal Test
- _Status: REVIEWED
- _Procedure: BSignOffEventActive == ON &&
  NTExitLighting != OFF &&
  NBatteryLowStateOfCharge == OK
- _Pass criteria: BSignOffEventStatus = ON
  NDippedBeamLeftStatus = ON
  NDippedBeamRightStatus = ON
  NSideLightLeftStatus = ON
  NSideLightRightStatus = ON
  NTailLightLeftStatus = ON
  NTailLightRightStatus = ON
- _Regression: Yes
- _Time [hr]: 0.1
- _Test environment: Lab-Car (auto)

## STC-BDY02-1618: Sign Off Event deactivation
Sign Off Event deactivation when Ignition State transits back to Awake above with door closed or keyfob enters back to Welcome Zone or vehicle gets unlock from lock again
- _Object type: Nominal Test
- _Status: REVIEWED
- _Procedure: BSignOffEventStatus = ON &&
  BSignOffEventActive == OFF
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF
- _Regression: Yes
- _Time [hr]: 0.1
- _Test environment: Lab-Car (auto)

## STC-BDY02-1619: Sign Off Event deactivation
Sign Off Event deactivation when the battery state of charge is low
- _Object type: Nominal Test
- _Status: REVIEWED
- _Procedure: BSignOffEventStatus = ON &&
  NBatteryLowStateOfCharge != OK
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF
- _Regression: Yes
- _Time [hr]: 0.1
- _Test environment: Lab-Car (auto)

## STC-BDY02-1620: Sign Off Event deactivation
Sign Off Event deactivation when the exit lighting is disable on central display
- _Object type: Nominal Test
- _Status: REVIEWED
- _Procedure: BSignOffEventStatus = ON &&
  NTExitLighting == OFF
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF
- _Regression: Yes
- _Time [hr]: 0.1
- _Test environment: Lab-Car (auto)

## STC-BDY02-1621: Sign Off Event deactivation
Sign Off Event deactivation when the exit lighting timer is reached
- _Object type: Nominal Test
- _Status: REVIEWED
- _Procedure: BSignOffEventStatus = ON &&
  NTExitLighting timer reached
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF
- _Regression: Yes
- _Time [hr]: 0.1
- _Test environment: Lab-Car (auto)

## STC-BDY02-1622: Sign Off Event lighting function timer
Sign Off Event lighting function timer shall be able to be configured by the user via Menu Stalk or contact screen
- _Object type: Nominal Test
- _Status: REVIEWED
- _Procedure: Central display exit lighting settings
- _Pass criteria: NTExitLighting
- _Regression: Yes
- _Time [hr]: 0.1
- _Test environment: Vehicle (static)

## STC-BDY02-1623
Sign Off Event lighting function activation when the DI Stalk is pulled towards the user, the door gets open after ignition state drops to Awake and the battery state of charge is not low
- _Object type: Nominal Test
- _Status: REVIEWED
- _Procedure: BSignOffEventActive == ON &&
  NFlashMainSwitch == Latched &&
  NBatteryLowStateOfCharge == OK
- _Pass criteria: BSignOffEventStatus = ON
  NDippedBeamLeftStatus = ON
  NDippedBeamRightStatus = ON
  NSideLightLeftStatus = ON
  NSideLightRightStatus = ON
  NTailLightLeftStatus = ON
  NTailLightRightStatus = ON
- _Regression: Yes
- _Time [hr]: 0.1
- _Test environment: Lab-Car (auto)

## STC-BDY02-1624: Exit lighting timer
The default exit lighting timer shall be 15s and be able to increase by 15s up to 60s maximum every time when pulling the DI stalk towards the steering wheel to a momentary position with Ignition state on Awake (0x2).
- _Object type: Nominal Test
- _Status: REVIEWED
- _Procedure: NIgnitionStatus == Awake &&
  NFlashMainSwitch == Flash
- _Pass criteria: NTExitLighting starts from 15s and increases by 15s up to 60s
- _Regression: Yes
- _Time [hr]: 0.1
- _Test environment: Vehicle (static)

## STC-BDY02-1625: Sign Off Event deactivation
Sign Off Event deactivation when ADI communication is in fault
- _Object type: Nominal Test
- _Status: REVIEWED
- _Procedure: BSignOffEventActive == ON &&
  ADI communication fault raised
- _Pass criteria: BSignOffEventActive = OFF
  NDippedBeamLeftStatus = OFF
  NDippedBeamRightStatus = OFF
  NSideLightLeftStatus = OFF
  NSideLightRightStatus = OFF
  NTailLightLeftStatus = OFF
  NTailLightRightStatus = OFF
- _Regression: No
- _Time [hr]: 0.1
- _Test environment: Vehicle (static)

## STC-BDY02-1138: DTRL deactivation with ignition state
To confirm DTRL deactivation when ignition state < 5
- _Object type: Nominal Test
- _Status: REVIEWED
- _Procedure: 1.Set NIgnitionStatus == Ignition (0x5)
  2.Activate DTRL function(DTRL Function available
  && NMasterLightSwitchPosition == OFF && NDippedBeamLeftStatus == Inactive && NDippedBeamRightStatus == Inactive)
  3.Set NIgnitionStatus !== Ignition (0x5)
- _Pass criteria: NDTRLLeftStatus = InActive NDTRLRightStatus = InActive
- _Regression: No
- _Time [hr]: 0.1
- _Test environment: Lab-Car (auto)

## STC-BDY02-217: DTRL control logic - Right Indicator ON (ID:STC-HMI01-204)
DTRL of the right hand shall be deactivated when right hand directional indicator is active
- _Object type: Cross Functional Test
- _Status: REVIEWED
- _Procedure: 1.NHazardStatus = 0x0 && NIndicatorLStatus =0x0 && NIndicatorRStatus = 0x0
  2.Set ignition status ≥ 5 && Master Light Switch Position = 0 || A
  3.Set NIndicatorRStatus = 0x1
  4.Set NIndicatorRStatus = 0x0
- _Pass criteria: 2.DTRL is active.
  NDTRLLeftStatus = (0x1) && NDTRLRightStatus = (0x1),
  NTailLightLeftStatus = (0x1) && NTailLightRightStatus = (0x1),
  NMasterLightStatus = (0x1)
  3.DTRL of the left hand is inactive.
  NDTRLLeftStatus = (0x1) && NDTRLRightStatus = (0x0),
  NTailLightLeftStatus = (0x1) && NTailLightRightStatus = (0x1),NMasterLightStatus = (0x1)
  4.DTRL is active.
  NDTRLLeftStatus = (0x1) && NDTRLRightStatus = (0x1),NMasterLightStatus = (0x1)
- _Regression: Yes
- _Time [hr]: 0.2
- _Test environment: Lab-Car (auto)

## STC-BDY02-225: DTRL control logic - Left Indicator ON
DTRL of the left hand shall be deactivated when left hand directional indicator is active
- _Object type: Nominal Test
- _Status: REVIEWED
- _Procedure: 1.NHazardStatus = 0x0 && NIndicatorLStatus =0x0 && NIndicatorRStatus = 0x0
  2.Set ignition status ≥ 5 && Master Light Switch Position = 0 || A
  3.Set NIndicatorLStatus = 0x1
  4.Set NIndicatorLStatus = 0x0
- _Pass criteria: 2.DTRL is active.
  NDTRLLeftStatus = (0x1) && NDTRLRightStatus = (0x1),
  NTailLightLeftStatus = (0x1) && NTailLightRightStatus = (0x1),
  NMasterLightStatus = (0x1)
  3.DTRL of the left hand is inactive.
  NDTRLLeftStatus = (0x0) && NDTRLRightStatus = (0x1),
  NMasterLightStatus = (0x1),
  NTailLightLeftStatus = (0x1) && NTailLightRightStatus = (0x1)
  4.DTRL is active.
  NDTRLLeftStatus = (0x1) && NDTRLRightStatus = (0x1),NMasterLightStatus = (0x1)
- _Regression: Yes
- _Time [hr]: 0.2
- _Test environment: Lab-Car (auto)

## STC-BDY02-222: DTRL control logic - Hazard ON
DTRL function shall be deactivated when hazard is active
- _Object type: Nominal Test
- _Status: REVIEWED
- _Procedure: 1.NHazardStatus = 0x0 && NIndicatorLStatus =0x0 && NIndicatorRStatus = 0x0
  2.Set ignition status ≥ 5 && Master Light Switch Position = 0 || A
  3.Set NHazardStatus= 0x1
  4.Set NHazardStatus= 0x0
- _Pass criteria: 2.DTRL is active.
  NDTRLLeftStatus = (0x1) && NDTRLRightStatus = (0x1), NTailLightLeftStatus = (0x1) && NTailLightRightStatus = (0x1)
  3.DTRL is inactive.
  NDTRLLeftStatus = (0x0) && NDTRLRightStatus = (0x0),
  NMasterLightStatus = (0x1),
  NTailLightLeftStatus = (0x1) && NTailLightRightStatus = (0x1)
  4.DTRL is active.
  NDTRLLeftStatus = (0x1) && NDTRLRightStatus = (0x1)
- _Regression: Yes
- _Time [hr]: 0.2
- _Test environment: Lab-Car (auto)

## STC-BDY02-1139: DTRL deactivation with MLS position
To confirm DTRL deactivation when Master Light Switch Position is set to Side Light or Dipped Beam position
- _Object type: Nominal Test
- _Status: REVIEWED
- _Procedure: 1.Set NIgnitionStatus == Ignition (0x5)
  2.Activate DTRL function(DTRL Function available
  && NMasterLightSwitchPosition == OFF && NDippedBeamLeftStatus == Inactive && NDippedBeamRightStatus == Inactive)
  3.Set Master Light Switch Position is set to Side Light or Dipped Beam position
- _Pass criteria: NDTRLLeftStatus = InActive NDTRLRightStatus = InActive
- _Regression: No
- _Time [hr]: 0.1
- _Test environment: Lab-Car (auto)

## STC-BDY02-1137: side & tail lamps illumination when DTRL lights are activated
To confirm side & tail lamps illumination when DTRL lights are activated
- _Object type: Nominal Test
- _Status: REVIEWED
- _Procedure: Activate DTRL function(DTRL Function available && NMasterLightSwitchPosition == AUTO
  && NRainLightLSignalError == no error && NLightSwitchRequest == ON && NLightSwitchReason == Daylight)
- _Pass criteria: BLH_HeadlampLEDActivateReq = Active
  BRH_HeadlampLEDActivateReq = Active
  NTailLightLeftStatus = Active
  NTailLightRightStatus = Active
- _Regression: No
- _Time [hr]: 0.1
- _Test environment: Lab-Car (auto)

## STC-BDY02-1142: DTRL Short circuit fault
To confirm DTRL lights diagnostic strategy when short circuit fault occurs
- _Object type: Nominal Test
- _Status: REVIEWED
- _Procedure: 1.Creat DTRL circuit fault i.e., short circuit fault
  2.After fault, make sure the drive feedback curent is out of normal operation thresholds
- _Pass criteria: NLHFrontLampActiveSts = DTRLLampInactive
  NRHFrontLampActiveSts = DTRLLampInactive
  2.A DTC shall be raised
  3.NDTRLClusterMessage = Fault
- _Regression: No
- _Time [hr]: 0.1
- _Test environment: Lab-Car (auto)

## STC-BDY02-1143: DTRL open circuit fault
To confirm DTRL lights diagnostic strategy when open circuit fault occurs
- _Object type: Nominal Test
- _Status: REVIEWED
- _Procedure: 1.Creat DTRL circuit fault i.e., open circuit fault
  2.After fault, make sure the drive feedback curent is out of normal operation thresholds
- _Pass criteria: NLHFrontLampActiveSts = DTRLLampInactive
  NRHFrontLampActiveSts = DTRLLampInactive
  2.A DTC shall be raised
  3.NDTRLClusterMessage = Fault
- _Regression: No
- _Time [hr]: 0.1
- _Test environment: Lab-Car (auto)

## STC-BDY02-1144: DTRL circuit circuit fault reset
To confirm DTRL lights fault reset with new ignition cycle
- _Object type: Nominal Test
- _Status: REVIEWED
- _Procedure: 1.Creat DTRL circuit fault i.e., Open circuit fault
  2.After fault, make sure the drive feedback curent is out of normal operation thresholds
  3.Start new ignition cycle
- _Pass criteria: NLHFrontLampActiveSts = DTRLLampInactive
  NRHFrontLampActiveSts = DTRLLampInactive
- _Regression: No
- _Time [hr]: 0.1
- _Test environment: Lab-Car (auto)

## STC-BDY02-382: Side markers activation for SAE market (ID:STC-CFG01-01-337)
Side markers activation when MLS= 1||2 for SAE market
- _Object type: Cross Functional Test
- _Status: REVIEWED
- _Procedure: 1.Set NVehicleMarket = USA || Canada
  2.Set NIgnitionStatus < 5
  3.Master Light Switch Position = 1 || 2
- _Pass criteria: NFrontLeftSideMarkerActvReq = Active &&
  NRearLeftSideMarkerActvReq = Active &&
  NFrontRightSideMarkerActvReq = Active &&
  NRearRightSideMarkerActvReq = Active
- _Regression: Yes
- _Time [hr]: 0.1
- _Test environment: Lab-Car (auto)

## STC-BDY02-1474: Side markers activation for SAE market
Side markers activation when ign>=5 for SAE market
- _Object type: Nominal Test
- _Status: REVIEWED
- _Procedure: 1.Set NVehicleMarket = USA || Canada
  2.Set NIgnitionStatus == (Ignition (0x5) || Powertrain Activation (0x6))
- _Pass criteria: NFrontLeftSideMarkerActvReq = Active &&
  NRearLeftSideMarkerActvReq = Active &&
  NFrontRightSideMarkerActvReq = Active &&
  NRearRightSideMarkerActvReq = Active
- _Regression: Yes
- _Time [hr]: 0.1
- _Test environment: Lab-Car (auto)

## STC-BDY02-383: Side markers activation for ECE market
Side markers activation with direction indicator function
- _Object type: Nominal Test
- _Status: REVIEWED
- _Procedure: 1.Set NVehicleMarket != (USA || Canada) && INIgnitionStatus ≥ 5
  Case 1:
  NRepeaterLeftOn == Active
  Case 2:
  NRepeaterRightOn == Active
- _Pass criteria: Case 1:
  NFrontLeftSideMarkerActvReq = Active &&
  NRearLeftSideMarkerActvReq = Inactive
  Case 2:
  NFrontRightSideMarkerActvReq= Active &&
  NRearRightSideMarkerActvReq = Inactive
- _Regression: Yes
- _Time [hr]: 0.1
- _Test environment: Lab-Car (auto)

## STC-BDY02-1147: Side marker Short circuit fault
To confirm Side marker lights diagnostic strategy when short circuit fault occurs
- _Object type: Nominal Test
- _Status: REVIEWED
- _Procedure: 1.Creat Side marker circuit fault i.e., short circuit fault
  2.After fault, make sure the drive feedback curent is out of normal operation thresholds
- _Pass criteria: NFrontLeftSideMarkerActiveStatus = Inactive
  NFrontRightSideMarkerActiveStatus = Inactive
  NRearLeftSideMarkerActiveStatus = Inactive
  NRearRightSideMarkerActiveStatus = Inactive
  2.A DTC shall be raised
  3.NSideMarkerClusterMessage = Fault
- _Regression: No
- _Time [hr]: 0.1
- _Test environment: Lab-Car (auto)

## STC-BDY02-1148: Side marker open circuit fault
To confirm Side marker lights diagnostic strategy when open circuit fault occurs
- _Object type: Nominal Test
- _Status: REVIEWED
- _Procedure: 1.Creat Side marker circuit fault i.e., open circuit fault
  2.After fault, make sure the drive feedback curent is out of normal operation thresholds
- _Pass criteria: NFrontLeftSideMarkerActiveStatus = Inactive
  NFrontRightSideMarkerActiveStatus = Inactive
  NRearLeftSideMarkerActiveStatus = Inactive
  NRearRightSideMarkerActiveStatus = Inactive
  2.A DTC shall be raised
  3.NSideMarkerClusterMessage = Fault
- _Regression: No
- _Time [hr]: 0.1
- _Test environment: Lab-Car (auto)

## STC-BDY02-1149: Side marker circuit circuit fault reset
To confirm Side marker lights fault reset with new ignition cycle
- _Object type: Nominal Test
- _Status: REVIEWED
- _Procedure: 1.Creat Side marker circuit fault i.e., Open circuit fault
  2.After fault, make sure the drive feedback curent is out of normal operation thresholds
  3.Start new ignition cycle
- _Pass criteria: NFrontLeftSideMarkerActiveStatus = Inactive
  NFrontRightSideMarkerActiveStatus = Inactive
  NRearLeftSideMarkerActiveStatus = Inactive
  NRearRightSideMarkerActiveStatus = Inactive
- _Regression: No
- _Time [hr]: 0.1
- _Test environment: Lab-Car (auto)

## STC-BDY02-1476: Brake light activation
To confirm brake lights activation with ignition
- _Object type: Nominal Test
- _Status: REVIEWED
- _Procedure: 1.Set NIgnitionStatus == PT Wake || Ignition || Powertrain Activation
  2.Press brake pedal:
  NBrakepedalStatus_Q == Valid && NBrakepedalStatus == Pressed
- _Pass criteria: NBrakeLightLStatus = Active
  NBrakeLightRStatus = Active
  NBrakeLightMiddleStatus = Active
- _Regression: Yes
- _Time [hr]: 0.1
- _Test environment: Lab-Car (auto)

## STC-BDY02-1478: Brake light activation
To confirm brake lights activation when quality signal is Faulty
- _Object type: Nominal Test
- _Status: REVIEWED
- _Procedure: 1.Set NIgnitionStatus == PT Wake || Ignition || Powertrain Activation
  2.Brake pedal quality signal is Faulty and Press brake pedal,
  NBrakepedalStatus_Q != Valid && NpBrake_Q == Valid && pBrake >= pBrakeThresholdActive
- _Pass criteria: NBrakeLightLStatus = Active
  NBrakeLightRStatus = Active
  NBrakeLightMiddleStatus = Active
- _Regression: No
- _Time [hr]: 0.1
- _Test environment: Lab-Car (auto)

## STC-BDY02-1479: Brake light activation
To confirm brake lights activation when quality signal and brake threshold both are Faulty
- _Object type: Nominal Test
- _Status: REVIEWED
- _Procedure: 1.Set NIgnitionStatus == PT Wake || Ignition || Powertrain Activation
  2.Brake pedal quality signal and brake threshold both are Faulty,
  NBrakepedalStatus_Q != Valid && NpBrake_Q != Valid
- _Pass criteria: NBrakeLightLStatus = Active
  NBrakeLightRStatus = Active
  NBrakeLightMiddleStatus = Active
- _Regression: No
- _Time [hr]: 0.1
- _Test environment: Lab-Car (auto)

## STC-BDY02-1151: Brake light activation with ESP request
To confirm brake lights activation when ESP requested
- _Object type: Nominal Test
- _Status: REVIEWED
- _Procedure: 1.Set NIgnitionStatus == PT Wake || Ignition || Powertrain Activation
  2.ESP requests brake light illumination, NDynBrkActive == Active || NBrakeLightRequest == Active
- _Pass criteria: Brake Light illumination shall be 100% pwm
- _Regression: No
- _Time [hr]: 0.1
- _Test environment: Lab-Car (auto)

## STC-BDY02-1480: Brake light activation
To confirm brake lights activation when ESP requested
- _Object type: Nominal Test
- _Status: REVIEWED
- _Procedure: 1.Set NIgnitionStatus == PT Wake || Ignition || Powertrain Activation
  2.Set NDynBrkActive == Active || NRWUActive == Active
- _Pass criteria: NBrakeLightLStatus = Active
  NBrakeLightRStatus = Active
  NBrakeLightMiddleStatus = Active
- _Regression: No
- _Time [hr]: 0.1
- _Test environment: Lab-Car (auto)

## STC-BDY02-1481: Brake light activation
To confirm brake lights activation when NgLongitudinal in Fault
- _Object type: Nominal Test
- _Status: REVIEWED
- _Procedure: 1.Set NIgnitionStatus == PT Wake || Ignition || Powertrain Activation
  2.Set NgLongitudinal_Q != Valid
- _Pass criteria: NBrakeLightLStatus = Active
  NBrakeLightRStatus = Active
  NBrakeLightMiddleStatus = Active
- _Regression: No
- _Time [hr]: 0.1
- _Test environment: Lab-Car (auto)

## STC-BDY02-415: Brake light function activation
Brake lights shall illuminate when deceleration rate is above 0.9 m/s2
- _Object type: Nominal Test
- _Status: REVIEWED
- _Procedure: 1.NIgntionState>=4
  2.Decelerate vehicle at the rate of change of wheel speed(nWheelFL,
  nWheelFR) is above 1.2 m/s2
- _Pass criteria: Brake lights shall be illuminated as long as the deceleration rate is above 0.9 m/s2.
  NBrakeLightLStatus =0x1
  NBrakeLightRStatus = 0x1
  NBrakeLightMiddleStatus =0x1
- _Regression: No
- _Time [hr]: 0.1
- _Test environment: Lab-Car (auto)

## STC-BDY02-419: Brake light function activation
Brake lights shall illuminate when deceleration rate is 1.0m/s2
- _Object type: Nominal Test
- _Status: REVIEWED
- _Procedure: 1.NIgntionState>=4
  2.Decelerate vehicle at the rate of change of wheel speed(nWheelFL,
  nWheelFR) is equal to 1.0m/s2
- _Pass criteria: Brake lights shall be illuminated as long as the deceleration rate is above 0.9 m/s2.
  NBrakeLightLStatus =0x1
  NBrakeLightRStatus = 0x1
  NBrakeLightMiddleStatus =0x1
- _Regression: No
- _Time [hr]: 0.1
- _Test environment: Lab-Car (auto)

## STC-BDY02-1482: Brake light function deactivation
To confirm brake lights deactivation when brake is released
- _Object type: Nominal Test
- _Status: REVIEWED
- _Procedure: 1.Set NIgnitionStatus == PT Wake || Ignition || Powertrain Activation
  2.NBrakepedalStatus_Q == Valid && NBrakepedalStatus != Pressed
- _Pass criteria: NBrakeLightLStatus = Inactive
  NBrakeLightRStatus = Inactive
  NBrakeLightMiddleStatus = Inactive
- _Regression: No
- _Time [hr]: 0.1
- _Test environment: Lab-Car (auto)

## STC-BDY02-1483: Brake light function deactivation
To confirm brake lights deactivation when ESP not requested the brake light
- _Object type: Nominal Test
- _Status: REVIEWED
- _Procedure: 1.Set NIgnitionStatus == PT Wake || Ignition || Powertrain Activation
  2.NDynBrkActive == Inactive &&
  NRWUActive == Inactive
- _Pass criteria: NBrakeLightLStatus = Inactive
  NBrakeLightRStatus = Inactive
  NBrakeLightMiddleStatus = Inactive
- _Regression: No
- _Time [hr]: 0.1
- _Test environment: Lab-Car (auto)

## STC-BDY02-1484: Brake light function deactivation
To confirm brake lights deactivation when brake is released
- _Object type: Nominal Test
- _Status: REVIEWED
- _Procedure: 1.Set NIgnitionStatus == PT Wake || Ignition || Powertrain Activation
  2.NBrakepedalStatus_Q != Valid && NpBrake_Q == Valid && pBrake < pBrakeThresholdInactive
- _Pass criteria: NBrakeLightLStatus = Inactive
  NBrakeLightRStatus = Inactive
  NBrakeLightMiddleStatus = Inactive
- _Regression: No
- _Time [hr]: 0.1
- _Test environment: Lab-Car (auto)

## STC-BDY02-1485: Brake light function deactivation
To confirm brake lights deactivation when gLong < gLongDeactiveThreshold
- _Object type: Nominal Test
- _Status: REVIEWED
- _Procedure: 1.Set NIgnitionStatus == PT Wake || Ignition || Powertrain Activation
  2.NBrakeLightRequest == Inactive && NgLongitudinal_Q == Valid && gLong < gLongDeactiveThreshold (0.9m/s2)
- _Pass criteria: NBrakeLightLStatus = Inactive
  NBrakeLightRStatus = Inactive
  NBrakeLightMiddleStatus = Inactive
- _Regression: No
- _Time [hr]: 0.1
- _Test environment: Lab-Car (auto)

## STC-BDY02-420: Brake light function inactive
Brake lights shall illuminate when deceleration rate is 0.9m/s2
- _Object type: Nominal Test
- _Status: REVIEWED
- _Procedure: 1.NIgntionState>=4
  2.Decelerate vehicle at the rate of change of wheel speed(nWheelFL,
  nWheelFR) is equal to 0.9m/s2
- _Pass criteria: Brake lights shall be inactive as long as the deceleration rate is <=0.9 m/s2.
  NBrakeLightLStatus =0x0
  NBrakeLightRStatus = 0x0
  NBrakeLightMiddleStatus =0x0
- _Regression: No
- _Time [hr]: 0.1
- _Test environment: Lab-Car (auto)

## STC-BDY02-1152: CHMS illumination with Brake light activation
To confirm CHMS illumination with brake lights activation
- _Object type: Nominal Test
- _Status: REVIEWED
- _Procedure: Activate brake lights, NBrakeLightLStatus == Active
  NBrakeLightRStatus == Active
  NBrakeLightMiddleStatus == Active
- _Pass criteria: NRHTailLampActivate_Req = Active
  NLHTailLampActivate_Req = Active
  BCHMS_LampActivateReq = Active
- _Regression: No
- _Time [hr]: 0.1
- _Test environment: Lab-Car (auto)

## STC-BDY02-1153: Brake light activation with 100% PWM
To confirm brake lights activation with 100% PWM
- _Object type: Nominal Test
- _Status: REVIEWED
- _Procedure: Activate brake lights, NBrakeLightLStatus == Active
  NBrakeLightRStatus == Active
  NBrakeLightMiddleStatus == Active
- _Pass criteria: NRHTailLampActivate_Req = Active
  NLHTailLampActivate_Req = Active
  BCHMS_LampActivateReq = Active
  NTailInboardLampIntensity_Req 100%NTailOutboardLampIntensity_Req = 100%
- _Regression: No
- _Time [hr]: 0.1
- _Test environment: Lab-Car (auto)

## STC-BDY02-1159: CHMS Short circuit fault
To confirm CHMS lights diagnostic strategy when short circuit fault occurs
- _Object type: Nominal Test
- _Status: REVIEWED
- _Procedure: 1.Creat CHMS circuit fault i.e., short circuit fault , NCHMS_LampActiveStatus = Fault
  2.After fault, make sure the drive feedback curent is out of normal operation thresholds
- _Pass criteria: NCHMS_LampActiveStatus = Inactive
  2.A DTC shall be raised
  3.NCHMSLightClusterMessage = Fault
- _Regression: No
- _Time [hr]: 0.1
- _Test environment: Lab-Car (auto)

## STC-BDY02-1160: CHMS open circuit fault
To confirm CHMS lights diagnostic strategy when open circuit fault occurs
- _Object type: Nominal Test
- _Status: REVIEWED
- _Procedure: 1.Creat CHMS circuit fault i.e., open circuit fault , NCHMS_LampActiveStatus = Fault
  2.After fault, make sure the drive feedback curent is out of normal operation thresholds
- _Pass criteria: NCHMS_LampActiveStatus = Inactive
  2.A DTC shall be raised
  3.NCHMSLightClusterMessage = Fault
- _Regression: No
- _Time [hr]: 0.1
- _Test environment: Lab-Car (auto)

## STC-BDY02-1161: CHMS circuit circuit fault reset
To confirm CHMS lights fault reset with new ignition cycle
- _Object type: Nominal Test
- _Status: REVIEWED
- _Procedure: 1.Creat CHMS circuit fault i.e., Open circuit fault, NCHMS_LampActiveStatus = Fault
  2.After fault, make sure the drive feedback curent is out of normal operation thresholds
  3.Start new ignition cycle
- _Pass criteria: NCHMS_LampActiveStatus = Inactive
- _Regression: No
- _Time [hr]: 0.1
- _Test environment: Lab-Car (auto)

## STC-BDY02-411: Hazard light function activation (ID:STC-ADA02-04-257)
Hazard function activation with hazard switch
- _Object type: Cross Functional Test
- _Status: REVIEWED
- _Procedure: 1.Set NIgnitionStatus >=0
  2.Press hazard switch, NHazardStatus =HAZARD_REQUEST
- _Pass criteria: Haazard light function shall be activated.
  NIndicatorLOn = Active &&
  NIndicatorROn = Active &&
  NRepeaterLeftOn= Active&&
  NRepeaterRightOn= Active&&
  HazardLightButtonIlumination= ON
- _Regression: Yes
- _Time [hr]: 0.2
- _Test environment: Lab-Car (auto)

## STC-BDY02-412: Hazard light function deactivation
Hazard function deactivation with hazard switch
- _Object type: Nominal Test
- _Status: REVIEWED
- _Procedure: 1.Activate hazard light function:
  Set NIgnitionStatus>=0 && NHazardStatus =HAZARD_REQUEST
  2.Again press hazard switch,NHazardStatus =HAZARD_REQUEST
- _Pass criteria: Haazard light function shall be deactivated.
  NIndicatorLOn = InActive &&
  NIndicatorROn = InActive &&
  NRepeaterLeftOn= InActive&&
  NRepeaterRightOn= InActive&&
  HazardLightButtonIlumination= OFF
- _Regression: Yes
- _Time [hr]: 0.2
- _Test environment: Lab-Car (auto)

## STC-BDY02-409: Hazard light function activated when crash is detected
Hazard function activation when crash is detected
- _Object type: Nominal Test
- _Status: REVIEWED
- _Procedure: 1.Set NIgnitionStatus >=0
  2.Set BCrashDetectHazardsON == Enabled && NCrashSeverity == Low Severity || High Severity
  3. Check NHazardStatus
- _Pass criteria: NHazardStatus = Active
- _Regression: Yes
- _Time [hr]: 0.2
- _Test environment: Lab-Car (auto)

## STC-BDY02-1162: Hazard light function deactivation when crash is detected
Hazard function deactivation when crash is detected
- _Object type: Nominal Test
- _Status: REVIEWED
- _Procedure: 1.Set NIgnitionStatus >=0
  2.Enable crash detection,
  CrashDetectHazardsON =1
  3.Press Hazard switch, NHazardSwitchPressStatus == Pressed
- _Pass criteria: NHazardStatus = Inactive
- _Regression: Yes
- _Time [hr]: 0.2
- _Test environment: Lab-Car (auto)

## STC-BDY02-1168: Emergency braking function activated
Emergency braking function activated when deceleration >= 6 m/s2 and vehicle speed >= 50 kph
- _Object type: Cross Functional Test
- _Status: REVIEWED
- _Procedure:
  1. Set NIgnitionStatus >= 5
  2. Set Vehicle deceleration >= 6 m/s2 && vehicle speed >= 50 kph
- _Pass criteria: To verify that EmergencyBrakeIndication == ON
- _Regression: No
- _Time [hr]: 0.2
- _Test environment: Lab-Car (auto)

## STC-BDY02-1169: Rear lamp stop and CHMS flash at 4 Hz
Rear lamp stop and CHMS flash at 4 Hz when the emergency braking function is active
- _Object type: Nominal Test
- _Status: REVIEWED
- _Procedure: Set NIgnitionStatus >= 5 && EmergencyBrakeIndication == ON
- _Pass criteria: To verify that Brake light && Central High Mounted Stop Lamp (CHMSL) flash at 4 Hz
- _Regression: No
- _Time [hr]: 0.2
- _Test environment: Lab-Car (auto)

## STC-BDY02-1636: Emergency braking switching off (deceleration)
If the emergency braking is active and the vehicle deceleration drops to <= 3.0 m/s2, the emergency braking should switch off
- _Object type: Nominal Test
- _Status: REVIEWED
- _Procedure: 1.EmergencyBrakeIndication == ON
  2.Vehicle deceleration <= 3 m/s2
- _Pass criteria: 2. EmergencyBrakeIndication == OFF
- _Regression: No
- _Time [hr]: 0.2
- _Test environment: Lab-Car (manual)

## STC-BDY02-1637: Emergency braking recovery
If the vehicle speed at the moment the emergency braking is deactivated s >=30 kph, normal lighting logic/behaviours applies
- _Object type: Nominal Test
- _Status: REVIEWED
- _Procedure: 1.EmergencyBrakeIndication == ON
  2.Vehicle deceleration <= 3 m/s2
  3. vehicle speed >= 30 kph
- _Pass criteria: 3.vehicle speed >= 30 kph
- _Regression: No
- _Time [hr]: 0.2
- _Test environment: Lab-Car (manual)

## STC-BDY02-1170: Hazard light deactivation in emergency braking when BEmergencyBrakeIndication == OFF (ID:STC-CFG02-01-1170)
To confirm Hazard light deactivation in emergency braking when BEmergencyBrakeIndication == OFF
- _Object type: Cross Functional Test
- _Status: REVIEWED
- _Procedure: 1.Set NIgnitionStatus >=2
  2.Disbale Emergency hazard function is turned to ON via User Preference in ICU, BEmergencyBrakeIndication == OFF
  3.Give brake pressure greater than threshold, pBrake >PEmergencyBrake
- _Pass criteria: NHazardStatus = Inactive
- _Regression: No
- _Time [hr]: 0.2
- _Test environment: Lab-Car (auto)

## STC-BDY02-1486: Hazard and panic alarm mode activation
To confirm Hazard and panic alarm mode activation when high voltage warning is activated
- _Object type: Nominal Test
- _Status: REVIEWED
- _Procedure: 1.Set NIgnitionStatus >=2
  2.Activate high voltage warning by Hybrid system with debouncing,
  BHybridHVWarnRequest == ON
  3.Press Hazard switch
- _Pass criteria: 2.NHazardStatus = Active
  NPanicModeActivated = Active
  DTC raised
  3.NHazardStatus == Inactive
  NPanicModeActivated == Inactive
- _Regression: No
- _Time [hr]: 0.1
- _Test environment: Lab-Car (auto)

## STC-BDY02-1487: Hazard and panic alarm mode deactivation
To confirm Hazard and panic alarm mode deactivation when high voltage warning is deactivated
- _Object type: Nominal Test
- _Status: REVIEWED
- _Procedure: 1.Set NIgnitionStatus >=2
  2.Activate high voltage warning by Hybrid system with debouncing,
  BHybridHVWarnRequest == ON
  3.High voltage warning is dismissed
- _Pass criteria: NHazardStatus == Inactive
  NPanicModeActivated == Inactive
- _Regression: No
- _Time [hr]: 0.1
- _Test environment: Lab-Car (auto)

## STC-BDY02-1172: Hazard switch button illumination and flashing during Hazard light activation
To confirm Hazard switch button illumination and flashing during Hazard light activation
- _Object type: Nominal Test
- _Status: REVIEWED
- _Procedure: 1.Set NIgnitionStatus >=2
  2.Enable Hazard with Emergency braking, NHazardStatus = active(pBrake >PEmergencyBrake && BEmergencyBrakeIndication == OFF)
- _Pass criteria: Hazard switch button shall be illuminated and flashing at 1.5 Hz frequency
- _Regression: No
- _Time [hr]: 0.2
- _Test environment: Lab-Car (auto)

## STC-BDY02-1171: Exterior lights flash frequency and Duty cycle during Hazard light activation
To confirm Exterior lights flash frequency and Duty cycle during Hazard light activation
- _Object type: Nominal Test
- _Status: REVIEWED
- _Procedure: 1.Set NIgnitionStatus >=2
  2.Enable Hazard with Emergency braking, NHazardStatus = active(pBrake >PEmergencyBrake && BEmergencyBrakeIndication == OFF)
- _Pass criteria: All exterior lights shall flash at 1.5Hz frequency with 50% duty cycle, NIndicatorLOn = Flash
  NIndicatorROn = Flash
  NRepeaterLeftOn = Flash
  NRepeaterRightOn = Flash
  NRHTailLampActivate_Req = Flash
  NLHTailLampActivate_Req = Flash
  HazardLightButtonIlumination= Flash
  Tell-tales displayed in flash
  Audible warning sounded
- _Regression: No
- _Time [hr]: 0.2
- _Test environment: Lab-Car (auto)

## STC-BDY02-1174: Exterior lights flash frequency and Duty cycle during Hazard light activation in ignition state <2
To confirm Exterior lights flash frequency and Duty cycle during Hazard light activation in ignition state <2
- _Object type: Nominal Test
- _Status: REVIEWED
- _Procedure: 1.Set NIgnitionStatus < 2
  2.Enable Hazard with Emergency braking, NHazardStatus = active(pBrake >PEmergencyBrake && BEmergencyBrakeIndication == OFF)
- _Pass criteria: Flashing at the same frequency:
  NIndicatorLOn = Flash
  NIndicatorROn = Flash
  NRepeaterLeftOn = Flash
  NRepeaterRightOn = Flash
  NRHTailLampActivate_Req = Flash
  NLHTailLampActivate_Req = Flash
  HazardLightButtonIlumination= Flash
- _Regression: No
- _Time [hr]: 0.2
- _Test environment: Lab-Car (auto)

## STC-BDY02-1165: Hazard light Short circuit fault
To confirm Hazard lights diagnostic strategy when short circuit fault occurs
- _Object type: Nominal Test
- _Status: REVIEWED
- _Procedure: 1.Creat Hazard light circuit fault i.e., short circuit fault
  2.After fault, make sure the drive feedback curent is out of normal operation thresholds
- _Pass criteria: NHazardSwitchPressStatus = Unpressed
  2.A DTC shall be raised
  3.NHazardCtrlClusterMessage = Fault
- _Regression: No
- _Time [hr]: 0.1
- _Test environment: Lab-Car (auto)

## STC-BDY02-1166: Hazard light open circuit fault
To confirm Hazard lights diagnostic strategy when open circuit fault occurs
- _Object type: Nominal Test
- _Status: REVIEWED
- _Procedure: 1.Creat Hazard light circuit fault i.e., open circuit fault
  2.After fault, make sure the drive feedback curent is out of normal operation thresholds
- _Pass criteria: NHazardSwitchPressStatus = Unpressed
  2.A DTC shall be raised
  3.NHazardCtrlClusterMessage = Fault
- _Regression: No
- _Time [hr]: 0.1
- _Test environment: Lab-Car (auto)

## STC-BDY02-1167: Hazard light circuit circuit fault reset
To confirm Hazard lights fault reset with new ignition cycle
- _Object type: Nominal Test
- _Status: REVIEWED
- _Procedure: 1.Creat Hazard light circuit fault i.e., Open circuit fault
  HSD11_2 = Open circuit or short to Gnd
  2.After fault, make sure the drive feedback curent is out of normal operation thresholds
  3.Start new ignition cycle
- _Pass criteria: NHazardSwitchPressStatus = Unpressed
- _Regression: No
- _Time [hr]: 0.1
- _Test environment: Lab-Car (auto)

## STC-BDY02-1638: Hazard Light Button DTC
The hazard button illumination shall be driven by a PWM HSD by the domain controller, so if a fault is detected a DTC shall be raised.
- _Object type: Nominal Test
- _Status: REVIEWED
- _Procedure: 1.Creat Hazard light circuit fault i.e., Open circuit fault
  HSD11_2 = Open circuit or short to Gnd
  2. Press the hazard button
- _Pass criteria: 2. DTC raised
- _Regression: No
- _Time [hr]: 0.2
- _Test environment: Lab-Car (manual)

## STC-BDY02-1175: Right Directional Indicator Activation
To confirm Right Directional Indicator Activation when DIMS stalk is pushed Upwards
- _Object type: Nominal Test
- _Status: REVIEWED
- _Procedure: 1.Set NIgnitionStatus == (Ignition || Powertrain Activation)
  2.Puh DIMS stalk Upwards, NDISwitch == Upwards
- _Pass criteria: NIndicatorRStatus = Active
- _Regression: No
- _Time [hr]: 0.1
- _Test environment: Lab-Car (auto)

## STC-BDY02-1176: Left Directional Indicator Activation
To confirm Left Directional Indicator Activation when DIMS stalk is pushed Downwards
- _Object type: Nominal Test
- _Status: REVIEWED
- _Procedure: 1.Set NIgnitionStatus == (Ignition || Powertrain Activation)
  2.Puh DIMS stalk Downwards, NDISwitch == Downwards
- _Pass criteria: NIndicatorLStatus = Active
- _Regression: No
- _Time [hr]: 0.1
- _Test environment: Lab-Car (auto)

## STC-BDY02-1177: Exterior lamps illumination when Right Directional Indicator is Activated
To confirm Exterior lamps illumination when Right Directional Indicator is Activated
- _Object type: Nominal Test
- _Status: REVIEWED
- _Procedure: 1.Set NIgnitionStatus == (Ignition || Powertrain Activation)
  2.Puh DIMS stalk Upwards, NDISwitch == Upwards
- _Pass criteria: NInidcatorROn = Active
  NRepeaterRightOn = Active
  NTailLightRightStatus = Active
- _Regression: No
- _Time [hr]: 0.1
- _Test environment: Lab-Car (auto)

## STC-BDY02-1178: Exterior lamps illumination when Left Directional Indicator is Activated
To confirm Exterior lamps illumination when Left Directional Indicator is Activated
- _Object type: Nominal Test
- _Status: REVIEWED
- _Procedure: 1.Set NIgnitionStatus == (Ignition || Powertrain Activation)
  2.Puh DIMS stalk Downwards, NDISwitch == Downwards
- _Pass criteria: NInidcatorLOn = Active
  NRepeaterLeftOn = Active
  NTailLightLeftStatus = Active
- _Regression: No
- _Time [hr]: 0.1
- _Test environment: Lab-Car (auto)

## STC-BDY02-1179: DI flash frequency with 50%
To confirm DI flash frequency
- _Object type: Nominal Test
- _Status: REVIEWED
- _Procedure: NIndicatorRStatus == Active ||
  NIndicatorLStatus == Active
- _Pass criteria: All related DI lamps flash at 1.5Hz with 50% duty cycle
- _Regression: No
- _Time [hr]: 0.1
- _Test environment: Lab-Car (auto)

## STC-BDY02-1180: Directional Indicator function deactivation with Hazard activation
To confirm DI function deactivation when hazard function is activated
- _Object type: Nominal Test
- _Status: REVIEWED
- _Procedure: 1.Activate Directional Indicator function, NIndicatorRStatus == Active ||
  NIndicatorLStatus == Active
  2.Press Hazard button, NHazardStatus == Active
- _Pass criteria: NIndicatorRStatus = Inactive
  NIndicatorLStatus = Inactive
  after the last flash
- _Regression: No
- _Time [hr]: 0.1
- _Test environment: Lab-Car (auto)

## STC-BDY02-1181: Tell tale display when Directional Indicator function activated
To confirm Tell tale display when Directional Indicator function activated
- _Object type: Nominal Test
- _Status: REVIEWED
- _Procedure: 1.Activate Directional Indicator function, NIndicatorRStatus == Active ||
  NIndicatorLStatus == Active
- _Pass criteria: Direction Indicator function status for the telltale, to indicate a green arrow consistent with the user direction request and an audible warning flash at 1.5 Hz frequency, synchronised with the direction indicator lights
- _Regression: No
- _Time [hr]: 0.1
- _Test environment: Lab-Car (manual)

## STC-BDY02-399: Left Direction indicator no of flashes
Left Direction indicator lights no of flashes equals to DILaneChangeFlashes
- _Object type: Nominal Test
- _Status: REVIEWED
- _Procedure: 1.Set NIgnitionStatus>=5
  2.Turn DIMS stalk left for less than DIMomentaryRequestTime i.e., 2sec(NDISwitch = 1 for <2sec)
- _Pass criteria: DILeftState_Active && Left Direction indicator light number of flashes equal to DILaneChangeFlashes i.e.,3 flashes,
  NInidcatorLOn = Active &&
  NRepeaterLeftOn= Active
- _Regression: Yes
- _Time [hr]: 0.1
- _Test environment: Lab-Car (auto)

## STC-BDY02-404: Right Direction indicator no of flashes
Right Direction indicator lights no of flashes equals to DILaneChangeFlashes
- _Object type: Nominal Test
- _Status: REVIEWED
- _Procedure: 1.Set NIgnitionStatus>=5
  2.Turn DIMS stalk right for less than DIMomentaryRequestTime i.e., 2sec(NDISwitch = 3 for <2sec)
- _Pass criteria: DIRighttState_Active && Right Direction indicator light number of flashes equal to DILaneChangeFlashes i.e.,3 flashes,
  NInidcatorROn = Active &&
  NRepeaterRightOn= Active
- _Regression: Yes
- _Time [hr]: 0.1
- _Test environment: Lab-Car (auto)

## STC-BDY02-405: Left Direction indicator no of flashes
Left Direction indicator lights no of flashes equals to DIMS stalk activation time
- _Object type: Nominal Test
- _Status: REVIEWED
- _Procedure: 1.Set NIgnitionStatus>=5
  2.Turn DIMS stalk left for longer than DIMomentaryRequestTime i.e., 2sec(NDISwitch = 1 for >2sec)
- _Pass criteria: DILeftState_Active && Left Direction indicator light shall flash for the duration DIMS stalk is activated,
  NInidcatorLOn = Active &&
  NRepeaterLeftOn= Active
- _Regression: Yes
- _Time [hr]: 0.1
- _Test environment: Lab-Car (auto)

## STC-BDY02-406: Right Direction indicator no of flashes
Right Direction indicator lights no of flashes equals to DIMS stalk activation time
- _Object type: Nominal Test
- _Status: REVIEWED
- _Procedure: 1.Set NIgnitionStatus>=5
  2.Turn DIMS stalk right for longer than DIMomentaryRequestTime i.e., 2sec(NDISwitch = 3 for >2sec)
- _Pass criteria: DIRighttState_Active && Right Direction indicator light shall flash for the duration DIMS stalk is activated,
  NInidcatorROn = Active &&
  NRepeaterRightOn= Active
- _Regression: Yes
- _Time [hr]: 0.1
- _Test environment: Lab-Car (auto)

## STC-BDY02-400: DIMS input received for opposite direction
Directional indicator function when DIMS input received for opposite direction
- _Object type: Nominal Test
- _Status: REVIEWED
- _Procedure: 1.Enable Left direction indicator light:
  Set NIgnitionStatus>=5 && NDISwitch = 1
  2.Turn DIMS stalk Right (NDISwitch = 3) immediately within no time
- _Pass criteria: Direction indicator function shall be Inactive for PostLaneChangeCancellationDelay i.e.,500ms,
  DIState_Inactive && NInidcatorLOn = InActive && NRepeaterLeftOn= InActive.
  After 500ms,Right direction indicator light shall be active,NInidcatorROn = Active &&
  NRepeaterRightOn= Active,
  NInidcatorLOn = InActive &&
  NRepeaterLeftOn= InActive
- _Regression: Yes
- _Time [hr]: 0.1
- _Test environment: Lab-Car (auto)

## STC-BDY02-407: DIMS input received for opposite direction
Directional indicator function when DIMS input received for opposite direction
- _Object type: Nominal Test
- _Status: REVIEWED
- _Procedure: 1.Enable Right direction indicator light:
  Set NIgnitionStatus >=5 && NDISwitch = 3
  2.Turn DIMS stalk Left(NDISwitch = 1) immediately within no time
- _Pass criteria: Direction indicator function shall be Inactive for PostLaneChangeCancellationDelay i.e.,500ms,
  DIState_Inactive && NInidcatorROn = InActive && NRepeaterRightOn= InActive.
  After 500ms,Left direction indicator light shall be active,NInidcatorLOn = Active &&
  NRepeaterLeftOn= Active,
  NInidcatorROn = InActive &&
  NRepeaterRightOn= InActive
- _Regression: Yes
- _Time [hr]: 0.1
- _Test environment: Lab-Car (auto)

## STC-BDY02-1185: Direction indicator lamps Short circuit fault
To confirm Direction indicator lamps diagnostic strategy when short circuit fault occurs
- _Object type: Nominal Test
- _Status: REVIEWED
- _Procedure: 1.Creat Direction indicator lamps circuit fault i.e., short circuit fault
  2.After fault, make sure the drive feedback curent is out of normal operation thresholds
- _Pass criteria: NFrontIndicatorLONActiveSts = Fault
  NFrontIndicatorRONActiveSts = Fault
  NLHSideRepeaterONSts = Fault
  NRHSideRepeaterONSts = Fault
  NHazardSwitchPressStatus = Unpressed
  2.A DTC shall be raised
  3.NHazardCtrlClusterMessage = Fault
- _Regression: No
- _Time [hr]: 0.1
- _Test environment: Lab-Car (auto)

## STC-BDY02-1186: Direction indicator lampsopen circuit fault
To confirm Direction indicator lamps diagnostic strategy when open circuit fault occurs
- _Object type: Nominal Test
- _Status: REVIEWED
- _Procedure: 1.Creat Direction indicator lamps circuit fault i.e., open circuit fault
  2.After fault, make sure the drive feedback curent is out of normal operation thresholds
- _Pass criteria: NFrontIndicatorLONActiveSts = Fault
  NFrontIndicatorRONActiveSts = Fault
  NLHSideRepeaterONSts = Fault
  NRHSideRepeaterONSts = Fault
  NHazardSwitchPressStatus = Unpressed
  2.A DTC shall be raised
  3.NHazardCtrlClusterMessage = Fault
- _Regression: No
- _Time [hr]: 0.1
- _Test environment: Lab-Car (auto)

## STC-BDY02-1187: Direction indicator lamps circuit circuit fault reset
To confirm Direction indicator lamps fault reset with new ignition cycle
- _Object type: Nominal Test
- _Status: REVIEWED
- _Procedure: 1.Creat Direction indicator lamps circuit fault i.e., Open circuit fault
  2.After fault, make sure the drive feedback curent is out of normal operation thresholds
  3.Start new ignition cycle
- _Pass criteria: LeftIndicatorFault,
  RightIndicatorFault,
  LeftRepeaterFault,
  RightRepeaterFault
- _Regression: No
- _Time [hr]: 0.1
- _Test environment: Lab-Car (auto)

## STC-BDY02-1317: Alarm status indication
To confirm Alarm status indication
- _Object type: Nominal Test
- _Status: REVIEWED
- _Procedure: 1.Set igniton state = any value
  2.NAlarmStatus == Triggered
- _Pass criteria: All the DIs shall Flash at a calibratable frequency AlarmIndicationActive (1.5Hz) and at a duty cycle calibrated AlarmTriggerDuty (50%)
- _Regression: No
- _Time [hr]: 0.2
- _Test environment: Lab-Car (manual)

## STC-BDY02-352: Fog light activation
- _Object type: Nominal Test
- _Status: REVIEWED
- _Procedure: 1.Set ignition status = 5||6
  2.Set MasterLightSwitch = A||2 and press centre button on the Master Light switch
- _Pass criteria: FogLightAvailable = True & Fog light shall illuminate
- _Regression: Yes
- _Time [hr]: 0.1
- _Test environment: Lab-Car (auto)

## STC-BDY02-356: Fog light NOT available
Fog light NOT available when ignition state<5
- _Object type: Nominal Test
- _Status: REVIEWED
- _Procedure: 1.Set ignition status < 5
  2.Set MasterLightSwitch = A||2 and press centre button on the Master Light switch
- _Pass criteria: FogLightAvailable = False & Fog light OFF
- _Regression: No
- _Time [hr]: 0.1
- _Test environment: Lab-Car (auto)

## STC-BDY02-357: Fog light NOT available
Fog light NOT available when Master Light Switch !=A||2
- _Object type: Nominal Test
- _Status: REVIEWED
- _Procedure: 1.Set ignition status = 5||6
  2.Set MasterLightSwitch != A||2 and press centre button on the Master Light switch
- _Pass criteria: FogLightAvailable = False & Fog light OFF
- _Regression: No
- _Time [hr]: 0.1
- _Test environment: Lab-Car (auto)

## STC-BDY02-358: Fog light deactivation
Fog light deactivation by exiting current ignition state
- _Object type: Negative Test
- _Status: REVIEWED
- _Procedure: 1.Activate Fog light(ignition status = 5||6 &&
  MasterLightSwitch = A||2)
  2.Set ignition status < 5
- _Pass criteria: 1.FogLightAvailable = True & Fog light shall illuminate
  2.FogLightAvailable = False & Fog light OFF
- _Regression: No
- _Time [hr]: 0.1
- _Test environment: Lab-Car (auto)

## STC-BDY02-359: Fog light deactivation
Fog light deactivation by master light switch
- _Object type: Negative Test
- _Status: REVIEWED
- _Procedure: 1.Activate Fog light(ignition status = 5||6 &&
  MasterLightSwitch = A||2)
  2.Set MasterLightSwitch != A||2
- _Pass criteria: 1.FogLightAvailable = True & Fog light shall illuminate
  2.FogLightAvailable = False & Fog light OFF
- _Regression: No
- _Time [hr]: 0.1
- _Test environment: Lab-Car (auto)

## STC-BDY02-501: Rear fog light activation
- _Object type: Nominal Test
- _Status: REVIEWED
- _Procedure: 1.Set Ignition state>=5
  2.Rear Fog light is Inactive,
  FogLightAvailable = True && FogLightActive= False
  3.MLS =Auto||Dipped
  4.Press Fog light switch i.e., press the centre button in Master Light Switch (rising edge)
- _Pass criteria: 4.FogLightActive= True, NFogLightRstatus= 0x1.
  Turn on the Fog Light
  Turn on the Dipped Beam.
  NFogLightRstatus =0x1
  NDippedBeamLeftStatus = (0x1)
  NDippedBeamRightStatus = (0x1)
- _Regression: Yes
- _Time [hr]: 0.1
- _Test environment: Lab-Car (auto)

## STC-BDY02-511: Fog light deactivation with ignition state
Fog light deactivation when ignition state is <5
- _Object type: Negative Test
- _Status: REVIEWED
- _Procedure: 1.Activate Rear Fog light :
  FogLightActive= True && NFogLightRstatus= 0x1
  2.Set ignition state <5
- _Pass criteria: 1.IFogLightActive= True
  Turn ON the Fog Light
  Turn ON the Dipped Beam
  2.FogLightActive= False
  Turn Off the Fog Light
  Turn off the Dipped Beam
- _Regression: No
- _Time [hr]: 0.1
- _Test environment: Lab-Car (auto)

## STC-BDY02-512: Fog light deactivation with MLS
Fog light deactivation when
MLS !=Auto|| Dipped
- _Object type: Negative Test
- _Status: REVIEWED
- _Procedure: 1.Activate Rear Fog light :
  FogLightActive= True && NFogLightRstatus= 0x1
  2.Set MLS !=Auto||Dipped
- _Pass criteria: 1.IFogLightActive= True
  Turn ON the Fog Light
  Turn ON the Dipped Beam
  2.FogLightActive= False
  Turn Off the Fog Light
  Turn off the Dipped Beam
- _Regression: No
- _Time [hr]: 0.1
- _Test environment: Lab-Car (auto)

## STC-BDY02-508: Rear fog light deactivation
- _Object type: Nominal Test
- _Status: REVIEWED
- _Procedure: 1.Activate Rear Fog light: FogLightActive= True &&
  Fog Light Switch press(rising edge )
  2.Press Fog light switch again i.e., press the centre button in Master Light Switch (rising edge)
- _Pass criteria: 2.FogLightActive= False
  Turn Off the Fog Light
  Turn off the Dipped Beam.
  NFogLightRstatus =0x0
  NDippedBeamLeftStatus = (0x0)
  NDippedBeamRightStatus = (0x0)
- _Regression: Yes
- _Time [hr]: 0.1
- _Test environment: Lab-Car (auto)

## STC-BDY02-502: Dipped beam kept ON
Dipped beam kept ON while MLS is in Auto position when Fog is activated
- _Object type: Nominal Test
- _Status: REVIEWED
- _Procedure: Activate Rear Fog light while the Master Light Switch is in AUTO position : FogLightActive= True &&
  Fog Light Switch press(rising edge ) && MasterLightSwitch = A
- _Pass criteria: Dipped beam kept ON.
  NDippedBeamLeftStatus = (0x1)
  NDippedBeamRightStatus = (0x1)
- _Regression: No
- _Time [hr]: 0.1
- _Test environment: Lab-Car (auto)

## STC-BDY02-503: Dipped beam with Fog light
Dipped beam while MLS in Auto position and when Fog light is deactivated
- _Object type: Nominal Test
- _Status: REVIEWED
- _Procedure: 1.Activate Rear Fog light while the Master Light Switch is in AUTO position : FogLightActive= True &&
  Fog Light Switch press(rising edge ) && MasterLightSwitch = A
  2.Deactivate the Fog light by pressing the the centre button in Master Light Switch (rising edge)
- _Pass criteria: 2. Dipped beam OFF
- _Regression: No
- _Time [hr]: 0.1
- _Test environment: Lab-Car (auto)

## STC-BDY02-509: Dipped beam with Fog light
Dipped beam while MLS in Side position and when Fog light is activated
- _Object type: Nominal Test
- _Status: REVIEWED
- _Procedure: 1.Activate Rear Fog light while the Master Light Switch is in AUTO position : FogLightActive= True &&
  Fog Light Switch press(rising edge ) && MasterLightSwitch = A
  2.Set Master light switch to Side position
- _Pass criteria: 2. Dipped beam OFF
- _Regression: No
- _Time [hr]: 0.1
- _Test environment: Lab-Car (auto)

## STC-BDY02-1639: Fog Light Lamp
The fog lamp shall be illuminated when the fog light function is activated
- _Object type: Nominal Test
- _Status: REVIEWED
- _Procedure: NFogLightRStatus == Active
- _Pass criteria: NFogLampDrvrStatus = Active
- _Regression: No
- _Time [hr]: 0.1
- _Test environment: Lab-Car (manual)

## STC-BDY02-504: Fog light telltale (ID: STC-HMI01-236)
Fog light telltale activation when Fog lights are active
- _Object type: Cross Functional Test
- _Status: REVIEWED
- _Procedure: Activate Rear Fog light :
  NFogLightRstatus= 0x1
- _Pass criteria: Rear Fog light telltale shall be displayed on driver display
- _Regression: Yes
- _Time [hr]: 0.1
- _Test environment: Lab-Car (manual)

## STC-BDY02-505: Fog light telltale inactive with default value
Rear fog light telltale shall be inactive when fog light signals in default value for 5 times
- _Object type: Nominal Test
- _Status: REVIEWED
- _Procedure: 1.Activate Rear Fog light :
  NFogLightRstatus= 0x1
  2.Simulate Rear Fog light signal as default value(NFogLightRstatus=0x3) and send 5 consecutive times onto the bus
- _Pass criteria: 1.Rear Fog light telltale shall be displayed on driver display
  2.Rear Fog light Telltale shall not be displayed
- _Regression: No
- _Time [hr]: 0.1
- _Test environment: Lab-Car (manual)

## STC-BDY02-506: Fog light telltale inactive with CAN timeout
Rear fog light telltale shall be inactive when CAN timeout occurs on the Rear Fog Light signal
- _Object type: Nominal Test
- _Status: REVIEWED
- _Procedure: 1.Activate Rear Fog light :
  NFogLightRstatus= 0x1
  2.Remove fog light switch in order to stop rear fog light signal for CAN timeout duration
- _Pass criteria: 1.Rear Fog light telltale shall be displayed on driver display
  2.Rear Fog light Telltale shall not be displayed
- _Regression: No
- _Time [hr]: 0.1
- _Test environment: Lab-Car (manual)

## STC-BDY02-510: Fog light switch LED illumination
LED in Fog light switch shall be illuminate when Fog light is active
- _Object type: Nominal Test
- _Status: REVIEWED
- _Procedure: 1.Activate Rear Fog light :
  FogLightActive= True && NFogLightRstatus= 0x1
  2.Deactivate Rear Fog light:
  FogLightActive= False &&NFogLightRstatus= 0x0
- _Pass criteria: 1.Illuminate the Fog Light Switch LED
  2.Deilluminate the Fog Light Switch LED
- _Regression: Yes
- _Time [hr]: 0.1
- _Test environment: Lab-Car (auto)

## STC-BDY02-1190: Fog lamp Short circuit fault
To confirm fog lamp diagnostic strategy when short circuit fault occurs
- _Object type: Nominal Test
- _Status: REVIEWED
- _Procedure: 1.Creat fog lamp circuit fault i.e., short circuit fault , NFogLampDrvrStatus = Fault
  2.After fault, make sure the drive feedback curent is out of normal operation thresholds
- _Pass criteria: NFogLampDrvrStatus = Fault
  2.A DTC shall be raised
  3.NFogLightClusterMessage = Fault
- _Regression: No
- _Time [hr]: 0.1
- _Test environment: Lab-Car (auto)

## STC-BDY02-1191: Fog lamp open circuit fault
To confirm fog lamp diagnostic strategy when open circuit fault occurs
- _Object type: Nominal Test
- _Status: REVIEWED
- _Procedure: 1.Creat fog lamp circuit fault i.e., open circuit fault , NFogLampDrvrStatus = Fault
  2.After fault, make sure the drive feedback curent is out of normal operation thresholds
- _Pass criteria: NFogLampDrvrStatus = Fault
  2.A DTC shall be raised
  3.NFogLightClusterMessage = Fault
- _Regression: No
- _Time [hr]: 0.1
- _Test environment: Lab-Car (auto)

## STC-BDY02-1192: Fog lamp circuit circuit fault reset
To confirm fog lamp fault reset with new ignition cycle
- _Object type: Nominal Test
- _Status: REVIEWED
- _Procedure: 1.Creat fog lamp circuit fault i.e., Open circuit fault, NFogLampDrvrStatus = Fault
  2.After fault, make sure the drive feedback curent is out of normal operation thresholds
  3.Start new ignition cycle
- _Pass criteria: NFogLampDrvrStatus = Inactive
- _Regression: No
- _Time [hr]: 0.1
- _Test environment: Lab-Car (auto)

## STC-BDY02-1194: License plate illumination
To confirm license plate illumination when side || dipped beam is active
- _Object type: Nominal Test
- _Status: REVIEWED
- _Procedure: 1.Activate Side lights or Dipped beam function(Set NIgnitionStatus =2 && NMasterLightStatus == Side Light || Dipped Beam)
- _Pass criteria: BLicenseLampActivateReq = Active && NLHLicenseLampActiveSts = Active
  NRHLicenseLampActiveSts = Active
- _Regression: No
- _Time [hr]: 0.1
- _Test environment: Lab-Car (auto)

## STC-BDY02-1197: License plate illumination deactivation
To confirm license plate illumination deactivation when side || dipped beam is inactive
- _Object type: Nominal Test
- _Status: REVIEWED
- _Procedure: 1.Activate Side lights or Dipped beam function(Set NIgnitionStatus =2 && NMasterLightStatus == Side Light || Dipped Beam)
  2.Inactivate Side lights or Dipped beam function,NMasterLightStatus !== Side Light || Dipped Beam
- _Pass criteria: BLicenseLampActivateReq = Inactive
- _Regression: No
- _Time [hr]: 0.1
- _Test environment: Lab-Car (auto)

## STC-BDY02-1200: License plate lamp Short circuit fault
To confirm license plate lamp diagnostic strategy when short circuit fault occurs
- _Object type: Nominal Test
- _Status: REVIEWED
- _Procedure: 1.Creat license plate lamp circuit fault i.e., short circuit fault , NLHLicenseLampActiveSts = Fault
  OR
  NRHLicenseLampActiveSts = Fault
  2.After fault, make sure the drive feedback curent is out of normal operation thresholds
- _Pass criteria: NLHLicenseLampActiveSts = Inactive
  NRHLicenseLampActiveSts = Inactive
  2.A DTC shall be raised
  3.NLicensePlateClusterMessage = Fault
- _Regression: No
- _Time [hr]: 0.1
- _Test environment: Lab-Car (auto)

## STC-BDY02-1201: License plate lamp open circuit fault
To confirm license plate lamp diagnostic strategy when open circuit fault occurs
- _Object type: Nominal Test
- _Status: REVIEWED
- _Procedure: 1.Creat license plate lamp circuit fault i.e., open circuit fault , NLHLicenseLampActiveSts = Fault
  OR
  NRHLicenseLampActiveSts = Fault
  2.After fault, make sure the drive feedback curent is out of normal operation thresholds
- _Pass criteria: NLHLicenseLampActiveSts = Inactive
  NRHLicenseLampActiveSts = Inactive
  2.A DTC shall be raised
  3.NLicensePlateClusterMessage = Fault
- _Regression: No
- _Time [hr]: 0.1
- _Test environment: Lab-Car (auto)

## STC-BDY02-1202: License plate lamp circuit circuit fault reset
To confirm license plate lamp fault reset with new ignition cycle
- _Object type: Nominal Test
- _Status: REVIEWED
- _Procedure: 1.Creat license plate lamp circuit fault i.e., Open circuit fault, NLHLicenseLampActiveSts = Fault
  OR
  NRHLicenseLampActiveSts = Fault
  2.After fault, make sure the drive feedback curent is out of normal operation thresholds
  3.Start new ignition cycle
- _Pass criteria: NLHLicenseLampActiveSts = Inactive
  NRHLicenseLampActiveSts = Inactive
- _Regression: No
- _Time [hr]: 0.1
- _Test environment: Lab-Car (auto)

## STC-BDY02-1209: Reverse light activation
To confirm reverse light activation when reverse gear is engaged
- _Object type: Nominal Test
- _Status: REVIEWED
- _Procedure: 1.Set NIgnitionStatus == Ignition || Activation
  2.Engage gear is in Reverse Gear, GearEngaged == Reverse Gear
- _Pass criteria: NReverseLightStatus = Active && NReverseLampActiveStatus = Active
- _Regression: No
- _Time [hr]: 0.1
- _Test environment: Lab-Car (auto)

## STC-BDY02-1210: Reverse light inactivation
To confirm reverse light inactivation when reverse gear is not engaged
- _Object type: Nominal Test
- _Status: REVIEWED
- _Procedure: 1.Activate Reverse light, (Set NIgnitionStatus == Ignition || Activation
  && GearEngaged == Reverse Gear)
  2.GearEngaged !== Reverse Gear
- _Pass criteria: NReverseLightStatus = inActive && NReverseLampActiveStatus = inActive
- _Regression: No
- _Time [hr]: 0.1
- _Test environment: Lab-Car (auto)

## STC-BDY02-1206: Reverse Light Short circuit fault
To confirm Reverse Light diagnostic strategy when short circuit fault occurs
- _Object type: Nominal Test
- _Status: REVIEWED
- _Procedure: 1.Creat Reverse Light circuit fault i.e., short circuit fault , NReverseLampActiveStatus = Fault
  2.After fault, make sure the drive feedback curent is out of normal operation thresholds
- _Pass criteria: 1.NReverseLampActiveStatus = Inactive
  2.A DTC shall be raised
  3.NReverseLightClusterMessage = Fault
- _Regression: No
- _Time [hr]: 0.1
- _Test environment: Lab-Car (auto)

## STC-BDY02-1207: Reverse Light open circuit fault
To confirm Reverse Light diagnostic strategy when open circuit fault occurs
- _Object type: Nominal Test
- _Status: REVIEWED
- _Procedure: 1.Creat Reverse Light circuit fault i.e., open circuit fault , NReverseLampActiveStatus = Fault
  2.After fault, make sure the drive feedback curent is out of normal operation thresholds
- _Pass criteria: 1.NReverseLampActiveStatus = Inactive
  2.A DTC shall be raised
  3.NReverseLightClusterMessage = Fault
- _Regression: No
- _Time [hr]: 0.1
- _Test environment: Lab-Car (auto)

## STC-BDY02-1208: Reverse Light circuit circuit fault reset
To confirm Reverse Light fault reset with new ignition cycle
- _Object type: Nominal Test
- _Status: REVIEWED
- _Procedure: 1.Creat Reverse Light circuit fault i.e., Open circuit fault, NReverseLampActiveStatus = Fault
  2.After fault, make sure the drive feedback curent is out of normal operation thresholds
  3.Start new ignition cycle
- _Pass criteria: NReverseLampActiveStatus = Inactive
- _Regression: No
- _Time [hr]: 0.1
- _Test environment: Lab-Car (auto)

## STC-BDY02-361: Parking light deactivation
Parking light deactivation when igniton state>2
- _Object type: Negative Test
- _Status: REVIEWED
- _Procedure: 1.Enable parking light function(Ignition status = 2 && NDISwitch=3||1)
  2.Set ignition status > 2
- _Pass criteria: 1.ParkingLightActive = True,
  Side lights, Side Marker and Tail lamps shall active when parking ligts are activated
  2.ParkingLightAvailable = False,
  Side lights, Side Marker and Tail lamps are OFF
- _Regression: No
- _Time [hr]: 0.1
- _Test environment: Lab-Car (auto)

## STC-BDY02-366: Parking light deactivation
Parking light deactivation with direction indicator stalk
- _Object type: Negative Test
- _Status: REVIEWED
- _Procedure: 1.Enable parking light function(Ignition status = 2 && NDISwitch=3||1)
  2.Set NDISwitch! = 3||1
- _Pass criteria: 1.ParkingLightActive = True,
  Side lights, Side Marker and Tail lamps shall active when parking ligts are activated
  2.ParkingLightAvailable = False,
  Side lights, Side Marker and Tail lamps are OFF
- _Regression: No
- _Time [hr]: 0.1
- _Test environment: Lab-Car (auto)

## STC-BDY02-371: Parking light deactivation
Parking light deactivation when battery is very low SOC
- _Object type: Negative Test
- _Status: REVIEWED
- _Procedure: 1.Enable parking light function(Ignition status = 2 && NDISwitch=3||1)
  2.Set INBatteryLowStateOfCharge = 1||2
- _Pass criteria: 1.ParkingLightActive = True,
  Side lights, Side Marker and Tail lamps shall active when parking ligts are activated
  2.ParkingLightAvailable = False,
  Side lights, Side Marker and Tail lamps are OFF
- _Regression: No
- _Time [hr]: 0.1
- _Test environment: Lab-Car (auto)

## STC-BDY02-367: Parking light function NOT available
Parking light function NOT available when ignition state>2
- _Object type: Nominal Test
- _Status: REVIEWED
- _Procedure: 1.Set ignition status > 2
  2.Set direction Indicator stalk in either left or right position (NDISwitch=3||1)
- _Pass criteria: ParkingLightAvailable = False,
  Side lights, Side Marker and Tail lamps shall remain OFF
- _Regression: No
- _Time [hr]: 0.1
- _Test environment: Lab-Car (auto)

## STC-BDY02-362: Parking light activation
- _Object type: Nominal Test
- _Status: REVIEWED
- _Procedure: 1.Set ignition status = 2
  2.Set direction Indicator stalk in either left or right position (NDISwitch=3||1)
- _Pass criteria: ParkingLightActive = True,
  Side lights, Side Marker and Tail lamps shall active when parking ligts are activated
- _Regression: Yes
- _Time [hr]: 0.1
- _Test environment: Lab-Car (auto)

## STC-BDY02-368: Parking light function NOT available
Parking light function NOT available with direction indicator stalk
- _Object type: Nominal Test
- _Status: REVIEWED
- _Procedure: 1.Set ignition status = 2
  2.Set NDISwitch!=3||1
- _Pass criteria: ParkingLightAvailable = False,
  Side lights, Side Marker and Tail lamps shall remain OFF
- _Regression: No
- _Time [hr]: 0.1
- _Test environment: Lab-Car (auto)

## STC-BDY02-369: Parking light function NOT available
Parking light function NOT available with low SOC
- _Object type: Nominal Test
- _Status: REVIEWED
- _Procedure: 1.Set NIgnitionStatus = Awake || Accessory
  2. Set NBatteryLowStateOfCharge != OK
  3.Set NDISwitch=3||1
- _Pass criteria: ParkingLightAvailable = False,
  Side lights, Side Marker and Tail lamps shall remain OFF
- _Regression: No
- _Time [hr]: 0.1
- _Test environment: Lab-Car (auto)

## STC-BDY02-513: Parking Light Left Active
Parking Light Left Activation
- _Object type: Nominal Test
- _Status: REVIEWED
- _Procedure: 1.Set NIgnitionStatus =2
  2. Parking Light Function Available && NDISwitch == Downwards
- _Pass criteria: NSideLightLeftStatus = Active
  NTailLightLeftStatus = Active
  BParkingLightStatus = Active
- _Regression: Yes
- _Time [hr]: 0.2
- _Test environment: Lab-Car (auto)

## STC-BDY02-532: Parking Light Left deActive with ignition state
Parking Light Left deActivation when existing current ignition state
- _Object type: Nominal Test
- _Status: REVIEWED
- _Procedure: 1.Set NIgnitionStatus =2 && Parking lights Inactive
  2.Operate Direction Indicator stalk to Left position, NDISwitch = 1 ( Rising edge)
  3.Set NIgnitionStatus > 2
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Left front Side Lamp, left Side Markers and left rear Tail Lamp shall be deactivated.
  ParkingLightLeftActive= False,
  NSideLStatus=0x0,
  NSidemarkerLeftStatus= 0x0,
  NTailLightLStatus= 0x0,
  NParkingLightsStaus = 0x00( both OFF)
- _Regression: No
- _Time [hr]: 0.2
- _Test environment: Lab-Car (auto)

## STC-BDY02-534: Parking Light Left deActive with low battery value
Parking Light Left deActivation with low battery voltage
- _Object type: Nominal Test
- _Status: REVIEWED
- _Procedure: 1.Set NIgnitionStatus =2 && Parking lights Inactive
  2.Operate Direction Indicator stalk to Left position, NDISwitch = 1 ( Rising edge)
  3.Set NBatteryUVP = 1||2
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Left front Side Lamp, left Side Markers and left rear Tail Lamp shall be deactivated.
  ParkingLightLeftActive= False,
  NSideLStatus=0x0,
  NSidemarkerLeftStatus= 0x0,
  NTailLightLStatus= 0x0,
  NParkingLightsStaus = 0x00( both OFF)
- _Regression: No
- _Time [hr]: 0.2
- _Test environment: Lab-Car (auto)

## STC-BDY02-518: Parking Light Right Active
Parking Light Right Activation
- _Object type: Nominal Test
- _Status: REVIEWED
- _Procedure: 1.Set NIgnitionStatus =2 && Parking lights Inactive
  2.Operate Direction Indicator stalk to Right position, NDISwitch = 3 ( Rising edge)
- _Pass criteria: Right front Side Lamp, Right Side Markers and Right rear Tail Lamp shall be activated.
  ParkingLightRightActive= True,
  NSideRStatus=0x1,
  NSidemarkerRightStatus= 0x1,
  NTailLightLStatus= 0x1,
  NParkingLightsStaus = 0x02( right on)
- _Regression: Yes
- _Time [hr]: 0.2
- _Test environment: Lab-Car (auto)

## STC-BDY02-533: Parking Light Right deActive with ignition state
Parking Light Right deActivation when existing current ignition state
- _Object type: Nominal Test
- _Status: REVIEWED
- _Procedure: 1.Set NIgnitionStatus =2 && Parking lights Inactive
  2.Operate Direction Indicator stalk to Right position, NDISwitch = 3 ( Rising edge)
  3.Set NIgnitionStatus > 2
- _Pass criteria: 2.Right front Side Lamp, Right Side Markers and Right rear Tail Lamp shall be activated.
  ParkingLightRightActive= True,
  NSideRStatus=0x1,
  NSidemarkerRightStatus= 0x1,
  NTailLightLStatus= 0x1,
  NParkingLightsStaus = 0x02( right on)
  3.Right front Side Lamp, Right Side Markers and Right rear Tail Lamp shall be deactivated.
  ParkingLightRightActive= False,
  NSideRStatus=0x0,
  NSidemarkerRightStatus= 0x0,
  NTailLightLStatus= 0x0,
  NParkingLightsStaus = 0x00( both OFF)
- _Regression: No
- _Time [hr]: 0.2
- _Test environment: Lab-Car (auto)

## STC-BDY02-535: Parking Light Right deActive with low battery value
Parking Light Right deActivation with low battery voltage
- _Object type: Nominal Test
- _Status: REVIEWED
- _Procedure: 1.Set NIgnitionStatus =2 && Parking lights Inactive
  2.Operate Direction Indicator stalk to Right position, NDISwitch = 3 ( Rising edge)
  3.Set NBatteryUVP = 1||2
- _Pass criteria: 2.Right front Side Lamp, Right Side Markers and Right rear Tail Lamp shall be activated.
  ParkingLightRightActive= True,
  NSideRStatus=0x1,
  NSidemarkerRightStatus= 0x1,
  NTailLightLStatus= 0x1,
  NParkingLightsStaus = 0x02( right on)
  3.Right front Side Lamp, Right Side Markers and Right rear Tail Lamp shall be deactivated.
  ParkingLightRightActive= False,
  NSideRStatus=0x0,
  NSidemarkerRightStatus= 0x0,
  NTailLightLStatus= 0x0,
  NParkingLightsStaus = 0x00( both OFF)
- _Regression: No
- _Time [hr]: 0.2
- _Test environment: Lab-Car (auto)

## STC-BDY02-514: Left & Right Parking Lights active
Both Left & Right Parking Lights activation
- _Object type: Nominal Test
- _Status: REVIEWED
- _Procedure: 1.Set NIgnitionStatus =2 && Parking lights Inactive
  2.Operate Direction Indicator Stalk in both directions just once i.e.,
  NDISwitch = 1 ( Rising edge) &&
  NDISwitch = 3 (Rising edge)
- _Pass criteria: Both left and right parking lights shall be activated.
  ParkingLightBothActive= True,
  NSideLStatus=0x1,
  NSidemarkerLeftStatus= 0x1,
  NTailLightLStatus= 0x1,
  NSideRStatus=0x1,
  NSidemarkerRightStatus= 0x1,
  NTailLightLStatus= 0x1,
  NParkingLightsStaus = 0x03( both on)
- _Regression: Yes
- _Time [hr]: 0.4
- _Test environment: Lab-Car (auto)

## STC-BDY02-536: Left & Right Parking Lights deactive with ignition state
Both Left & Right Parking Lights deactivation while exiting current ignition state
- _Object type: Nominal Test
- _Status: REVIEWED
- _Procedure: 1.Set NIgnitionStatus =2 && Parking lights Inactive
  2.Operate Direction Indicator Stalk in both directions just once i.e.,
  NDISwitch = 1 ( Rising edge) &&
  NDISwitch = 3 (Rising edge)
  3.Set NIgnitionStatus > 2
- _Pass criteria: 2.Both left and right parking lights shall be activated.
  ParkingLightBothActive= True,
  NSideLStatus=0x1,
  NSidemarkerLeftStatus= 0x1,
  NTailLightLStatus= 0x1,
  NSideRStatus=0x1,
  NSidemarkerRightStatus= 0x1,
  NTailLightLStatus= 0x1,
  NParkingLightsStaus = 0x03( both on)
  3.Both left and right parking lights shall be deactivated.
  ParkingLightBothActive= False,
  NSideLStatus=0x0,
  NSidemarkerLeftStatus= 0x0,
  NTailLightLStatus= 0x0,
  NSideRStatus=0x0,
  NSidemarkerRightStatus= 0x0,
  NTailLightLStatus= 0x0,
  NParkingLightsStaus = 0x00( both OFF)
- _Regression: No
- _Time [hr]: 0.4
- _Test environment: Lab-Car (auto)

## STC-BDY02-537: Left & Right Parking Lights deactive with low battery value
Both Left & Right Parking Lights deactivation with low battery voltage
- _Object type: Nominal Test
- _Status: REVIEWED
- _Procedure: 1.Set NIgnitionStatus =2 && Parking lights Inactive
  2.Operate Direction Indicator Stalk in both directions just once i.e.,
  NDISwitch = 1 ( Rising edge) &&
  NDISwitch = 3 (Rising edge)
  3.Set NBatteryUVP = 1||2
- _Pass criteria: 2.Both left and right parking lights shall be activated.
  ParkingLightBothActive= True,
  NSideLStatus=0x1,
  NSidemarkerLeftStatus= 0x1,
  NTailLightLStatus= 0x1,
  NSideRStatus=0x1,
  NSidemarkerRightStatus= 0x1,
  NTailLightLStatus= 0x1,
  NParkingLightsStaus = 0x03( both on)
  3.Both left and right parking lights shall be deactivated.
  ParkingLightBothActive= False,
  NSideLStatus=0x0,
  NSidemarkerLeftStatus= 0x0,
  NTailLightLStatus= 0x0,
  NSideRStatus=0x0,
  NSidemarkerRightStatus= 0x0,
  NTailLightLStatus= 0x0,
  NParkingLightsStaus = 0x00( both OFF)
- _Regression: No
- _Time [hr]: 0.4
- _Test environment: Lab-Car (auto)

## STC-BDY02-519: Parking Light Left deactive
Parking Light Left deactivation
- _Object type: Nominal Test
- _Status: REVIEWED
- _Procedure: 1.Set NIgnitionStatus =2 && Parking lights Inactive
  2.Operate Direction Indicator stalk to Left position, ParkingLightLeftActive= True && NDISwitch = 1 ( Rising edge)
  3.Operate Direction indicator again to same side, NDISwitch = 1 ( Rising edge)
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Parking light on that side(left) shall be deactivated.
  ParkingLightLeftActive= False
  NSideLStatus=0x0,
  NSidemarkerLeftStatus= 0x0,
  NTailLightLStatus= 0x0
- _Regression: Yes
- _Time [hr]: 0.2
- _Test environment: Lab-Car (auto)

## STC-BDY02-520: Parking Light Right deactive
Parking Light Right deactivation
- _Object type: Nominal Test
- _Status: REVIEWED
- _Procedure: 1.Set NIgnitionStatus =2 && Parking lights Inactive
  2.Operate Direction Indicator stalk to Right position, ParkingLightRightActive= True && NDISwitch = 3 ( Rising edge)
  3.Operate Direction indicator again to same side, NDISwitch = 3 ( Rising edge)
- _Pass criteria: 2.Right front Side Lamp, Right Side Markers and Right rear Tail Lamp shall be activated.
  ParkingLightRightActive= True,
  NSideRStatus=0x1,
  NSidemarkerRightStatus= 0x1,
  NTailLightRStatus= 0x1,
  NParkingLightsStaus = 0x02( Right on)
  3.Parking light on that side(Right ) shall be deactivated.
  ParkingLightRight Active= False
  NSideRStatus=0x0,
  NSidemarkerRightStatus= 0x0,
  NTailLightRStatus= 0x0
- _Regression: Yes
- _Time [hr]: 0.2
- _Test environment: Lab-Car (auto)

## STC-BDY02-523: Left parking light activation with Right light already in active state
Left Parking Light activation while Right light was in active state
- _Object type: Nominal Test
- _Status: REVIEWED
- _Procedure: 1.Set NIgnitionStatus =2 && Parking lights Inactive
  2.Operate Direction indicator to Right side, NDISwitch = 3 ( Rising edge)
  3.Operate Direction indicator to Left side, NDISwitch = 1 ( Rising edge)
- _Pass criteria: 2.Right front Side Lamp, Right Side Markers and Right rear Tail Lamp shall be activated.
  ParkingLightRightActive= True,
  NSideRStatus=0x1,
  NSidemarkerRightStatus= 0x1,
  NTailLightLStatus= 0x1,
  NParkingLightsStaus = 0x02( right on)
  3.Both left and right parking lights shall be activated.
  ParkingLightBothActive= True,
  NSideLStatus=0x1,
  NSidemarkerLeftStatus= 0x1,
  NTailLightLStatus= 0x1,
  NSideRStatus=0x1,
  NSidemarkerRightStatus= 0x1,
  NTailLightRStatus= 0x1,
  NParkingLightsStaus = 0x03( both on)
- _Regression: No
- _Time [hr]: 0.2
- _Test environment: Lab-Car (auto)

## STC-BDY02-524: Right parking light activation with Left light already in active state
Right Parking Light activation while Left light was in active state
- _Object type: Nominal Test
- _Status: REVIEWED
- _Procedure: 1.Set NIgnitionStatus =2 && Parking lights Inactive
  2.Operate Direction indicator to Left side, NDISwitch = 1 ( Rising edge)
  3.Operate Direction indicator to Right side, NDISwitch = 3 ( Rising edge)
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Both left and right parking lights shall be activated.
  ParkingLightBothActive= True,
  NSideLStatus=0x1,
  NSidemarkerLeftStatus= 0x1,
  NTailLightLStatus= 0x1,
  NSideRStatus=0x1,
  NSidemarkerRightStatus= 0x1,
  NTailLightRStatus= 0x1,
  NParkingLightsStaus = 0x03( both on)
- _Regression: No
- _Time [hr]: 0.2
- _Test environment: Lab-Car (auto)

## STC-BDY02-525: Both Parking Lights deactive
Both Left & Right Parking Lights (Right followed by Left)deactivation when both parking lights are active
- _Object type: Nominal Test
- _Status: REVIEWED
- _Procedure: 1.Set NIgnitionStatus =2 && Parking lights Inactive
  2.Operate Direction Indicator Stalk in both directions just once i.e.,
  NDISwitch = 1 ( Rising edge) &&
  NDISwitch = 3 (Rising edge)
  3.Operate Direction indicator to Left side, NDISwitch = 1 ( Rising edge)
  4.Operate Direction indicator to Right side, NDISwitch = 3 ( Rising edge)
- _Pass criteria: 2.Both left and right parking lights shall be activated.
  ParkingLightBothActive= True,
  NSideLStatus=0x1,
  NSidemarkerLeftStatus= 0x1,
  NTailLightLStatus= 0x1,
  NSideRStatus=0x1,
  NSidemarkerRightStatus= 0x1,
  NTailLightRStatus= 0x1,
  NParkingLightsStaus = 0x03( both on)
  3.Parking light on that side(left) shall be deactivated and Right side shall be in active state.
  ParkingLightLeftActive= False
  NSideLStatus=0x0,
  NSidemarkerLeftStatus= 0x0,
  NTailLightLStatus= 0x0,
  NSideRStatus=0x1,
  NSidemarkerRightStatus= 0x1,
  NTailLightRStatus= 0x1,
  NParkingLightsStaus = 0x02( Right on)
  4.Both left and right parking lights shall be deactivated.
  ParkingLightBothActive= False,
  NSideLStatus=0x0,
  NSidemarkerLeftStatus= 0x0,
  NTailLightLStatus= 0x0,
  NSideRStatus=0x0,
  NSidemarkerRightStatus= 0x0,
  NTailLightRStatus= 0x0,
  NParkingLightsStaus = 0x00( both OFF)
- _Regression: No
- _Time [hr]: 0.2
- _Test environment: Lab-Car (auto)

## STC-BDY02-527: Left Parking light telltale
Left Parking Light status to DriverDisplay
- _Object type: Nominal Test
- _Status: REVIEWED
- _Procedure: Activate Left Parking light:
  Set NIgnitionStatus =2 && NDISwitch = 1 ( Rising edge)
- _Pass criteria: Status of the Left Parking Light shall be communicated to the cluster
- _Regression: Yes
- _Time [hr]: 0.2
- _Test environment: Lab-Car (manual)

## STC-BDY02-528: Right Parking light telltale
Right Parking Light status to DriverDisplay
- _Object type: Nominal Test
- _Status: REVIEWED
- _Procedure: Activate Right Parking light:
  Set NIgnitionStatus =2 && NDISwitch = 3 ( Rising edge)
- _Pass criteria: Status of the Right Parking Light shall be communicated to the cluster
- _Regression: Yes
- _Time [hr]: 0.2
- _Test environment: Lab-Car (manual)

## STC-BDY02-515: Parking lights telltale
Left & Right Parking Lights status to DriverDisplay
- _Object type: Nominal Test
- _Status: REVIEWED
- _Procedure: Activate Left & Right Parking light:
  Set NIgnitionStatus =2 && NDISwitch = 1 ( Rising edge) && NDISwitch = 3 ( Rising edge)
- _Pass criteria: Status of the both Left & Right Parking Lights shall be communicated to the cluster
- _Regression: Yes
- _Time [hr]: 0.2
- _Test environment: Lab-Car (manual)

## STC-BDY02-529: DCU awake with Left parking light
DCU shall stay awake in ignition 0,1 while Left parking light is active
- _Object type: Nominal Test
- _Status: REVIEWED
- _Procedure: 1.Activate Left Parking light:
  Set NIgnitionStatus =2 && NDISwitch = 1 ( Rising edge)
  2.Deactive Left Parking light:NDISwitch = 1 ( Rising edge)
- _Pass criteria:
  1. DCU shall stay awake in Ignition 0,1 until left parking light is active
  2.DCU shall no longer be awake
- _Regression: No
- _Time [hr]: 0.2
- _Test environment: Lab-Car (manual)

## STC-BDY02-530: DCU awake with Right parking light
DCU shall stay awake in ignition 0,1 while Right parking light is active
- _Object type: Nominal Test
- _Status: REVIEWED
- _Procedure: 1.Activate Right Parking light:
  Set NIgnitionStatus =2 && NDISwitch = 3 ( Rising edge)
  2.Deactive Right Parking light:NDISwitch = 3 ( Rising edge)
- _Pass criteria:
  1. DCU shall stay awake in Ignition 0,1 until Right parking light is active
  2.DCU shall no longer be awake
- _Regression: No
- _Time [hr]: 0.2
- _Test environment: Lab-Car (manual)

## STC-BDY02-531: DCU awake with parking lights
DCU shall stay awake in ignition 0,1 while parking lights are active
- _Object type: Nominal Test
- _Status: REVIEWED
- _Procedure: 1.Activate Parking lights:
  Set NIgnitionStatus =2 && NDISwitch = 1 ( Rising edge) && NDISwitch = 3 ( Rising edge)
  2.Deactive Left Parking light: NDISwitch = 1 ( Rising edge)
  3.Deactive Right Parking light: NDISwitch = 3 ( Rising edge)
- _Pass criteria:
  1. DCU shall stay awake in Ignition 0,1 until any of the parking light is active
  2.DCU shall stay awake in Ignition 0,1 until any of the parking light is active
  3.DCU shall no longer be awake
- _Regression: No
- _Time [hr]: 0.2
- _Test environment: Lab-Car (manual)

## STC-BDY02-238: LH brake/Tail lamp output - S/C(GND)
DTC B122211 for LH brake/Tail lamp output is short to ground
- _Object type: Fault Test
- _Status: REVIEWED
- _Procedure: 1.Set ignition state to 1
  2.Short LH brake/Tail lamp output pin(xx) to ground(xx) for a duration of fault calibratable debounce period
  3.Remove the short b/w ouput pin to ground after fault calibratable debounce period
  4.Repeat steps 2,3 for all the ignition states
- _Pass criteria: 2.DTC B122211 shall be logged in current state in ZC1.
  Check cluster message CAN value.
  3.DTC B122211 shall be in healed state in ZC1.
  No cluster message CAN value.
- _Regression: No
- _Time [hr]: 0.4
- _Test environment: Lab-Car (auto)

## STC-BDY02-239: RH brake/Tail lamp output - S/C(GND)
DTC B12111 RH brake/Tail lamp output is short to ground
- _Object type: Fault Test
- _Status: REVIEWED
- _Procedure: 1.Set ignition state to 1
  2.Short RH brake/Tail lamp output pin(xx) to ground(xx) for a duration of fault calibratable debounce period
  3.Remove the short b/w ouput pin to ground after fault calibratable debounce period
  4.Repeat steps 2,3 for all the ignition states
- _Pass criteria: 2.DTC B12111 shall be logged in current state in ZC1.
  Check cluster message CAN value.
  3.DTC B12111 shall be in healed state in ZC1.
  No cluster message CAN value.
- _Regression: No
- _Time [hr]: 0.4
- _Test environment: Lab-Car (auto)

## STC-BDY02-240: Master light switch - voltage out of range
DTC B12011C Master light switch output voltage is out of range
- _Object type: Fault Test
- _Status: REVIEWED
- _Procedure: 1.Set ignition state to 1
  2.Short the master light switch output pin(xx) to battery voltage pin(xx) or open the output pin(xx) for a duration of fault calibratable debounce period
  3.Remove the short b/w ouput pin to battery after fault calibratable debounce period
  4.Repeat steps 2,3 for all the ignition states
- _Pass criteria: 2.DTC B12011Cshall be logged in current state in ZC1.
  Check cluster message CAN value.
  3.DTC B12011C shall be in healed state in ZC1.
  No cluster message CAN value.
- _Regression: No
- _Time [hr]: 0.4
- _Test environment: Lab-Car (auto)

## STC-BDY02-241: LH LED headlamp - S/C(GND)
DTC B122011 LH LED headlamp output short circuit to ground
- _Object type: Fault Test
- _Status: REVIEWED
- _Procedure: 1.Set ignition state to 1
  2.Short left hand headlamp output pin(xx) to ground(xx) for a duration of fault calibratable debounce period
  3.Remove the short b/w ouput pin to ground after fault calibratable debounce period
  4.Repeat steps 2,3 for all the ignition states
- _Pass criteria: 2.DTC B122011 shall be logged in current state in ZA1.
  Check cluster message CAN value.
  3.DTC B122011 shall be in healed state in ZA1.
  No cluster message CAN value.
- _Regression: No
- _Time [hr]: 0.4
- _Test environment: Lab-Car (auto)

## STC-BDY02-243: RH LED headlamp - S/C(GND)
DTC B121F11 RH LED headlamp output short circuit to ground
- _Object type: Fault Test
- _Status: REVIEWED
- _Procedure: 1.Set ignition state to 1
  2.Short right hand headlamp output pin(xx) to ground(xx) for a duration of fault calibratable debounce period
  3.Remove the short b/w ouput pin to ground after fault calibratable debounce period
  4.Repeat steps 2,3 for all the ignition states
- _Pass criteria: 2.DTC B121F11 shall be logged in current state in ZA1.
  Check cluster message CAN value.
  3.DTC B121F11 shall be in healed state in ZA1.
  No cluster message CAN value.
- _Regression: No
- _Time [hr]: 0.4
- _Test environment: Lab-Car (auto)

## STC-BDY02-468: Left lamp -shrt to GND
Main beam headlamp output left side-short to ground
- _Object type: Fault Test
- _Status: REVIEWED
- _Procedure: 1.Set ignition state to 1
  2.Short the main beam headlamp left side output pin(xx) to ground pin(xx) for a duration of fault calibratable debounce period
  3.Remove the short b/w ouput pin to ground after fault calibratable debounce period
  4.Repeat steps 2,3 for all other ignition states
- _Pass criteria: 2.DTC XXX shall be logged in current state in ZA1.
  Check for cluster message CAN value.
  3.DTC XXX shall be in healed state in ZA1.
  No cluster message CAN value.
- _Regression: No
- _Time [hr]: 0.5
- _Test environment: Lab-Car (auto)

## STC-BDY02-469: Left lamp -shrt to BATT or Open ckt
Main beam headlamp output left side-short to battery or open circuit
- _Object type: Fault Test
- _Status: REVIEWED
- _Procedure: 1.Set ignition state to 1
  2.Short the main beam headlamp left side output pin(xx) to battery voltage pin(xx) or open the output pin(xx) for a duration of fault calibratable debounce period
  3.Remove the short b/w ouput pin to battery after fault calibratable debounce period
  4.Repeat steps 2,3 for all other ignition states
- _Pass criteria: 2.DTC XXX shall be logged in current state in ZA1.
  Check cluster message CAN value.
  3.DTC XXX shall be in healed state in ZA1.
  No cluster message CAN value.
- _Regression: No
- _Time [hr]: 0.5
- _Test environment: Lab-Car (auto)

## STC-BDY02-470: Right lamp -shrt to GND
Main beam headlamp output right side-short to ground
- _Object type: Fault Test
- _Status: REVIEWED
- _Procedure: 1.Set ignition state to 1
  2.Short the main beam headlamp right side output pin(xx) to ground pin(xx) for a duration of fault calibratable debounce period
  3.Remove the short b/w ouput pin to ground after fault calibratable debounce period
  4.Repeat steps 2,3 for all other ignition states
- _Pass criteria: 2.DTC XXX shall be logged in current state in ZA1.
  Check cluster message CAN value.
  3.DTC XXX shall be in healed state in ZA1.
  No cluster message CAN value.
- _Regression: No
- _Time [hr]: 0.5
- _Test environment: Lab-Car (auto)

## STC-BDY02-471: Right lamp -shrt to BATT or Open ckt
Main beam headlamp output rught side-short to battery or open circuit
- _Object type: Fault Test
- _Status: REVIEWED
- _Procedure: 1.Set ignition state to 1
  2.Short the main beam headlamp right side output pin(xx) to battery voltage pin(xx) or open the output pin(xx) for a duration of fault calibratable debounce period
  3.Remove the short b/w ouput pin to battery after fault calibratable debounce period
  4.Repeat steps 2,3 for all other ignition states
- _Pass criteria: 2.DTC XXX shall be logged in current state in ZA1.
  Check for cluster message CAN value.
  3.DTC XXX shall be in healed state in ZA1.
  No cluster message CAN value.
- _Regression: No
- _Time [hr]: 0.5
- _Test environment: Lab-Car (auto)

## STC-BDY02-1368: SW Composition ExteriorLightingSafetyZa1
Composition Check
- _Object type: Misuse Test
- _Status: REVIEWED
- _Procedure: The SW composition ExteriorLightingSafetyZa1 implementing the safety monitoring of this function is designed.
- _Pass criteria: Verify that the SW composition is the only connected to the actuations of the outputs.
- _Regression: No
- _Time [hr]: 0.1
- _Test environment: HIL (manual)

## STC-BDY02-1503: SW Composition Master Light Control
Composition Check
- _Object type: Misuse Test
- _Status: REVIEWED
- _Procedure: The SW composition Master Light Control is defined.
- _Pass criteria: Verify that the compositions Master Light Control is not connected to any actuation of the outputs.
- _Regression: No
- _Time [hr]: 0.1
- _Test environment: HIL (manual)

## STC-BDY02-1369: High Side Command Headlamp
The ExteriorLightingSafetyZa1 command :
Headlamp_Ctrl_PWR_RH (HSD11_2)
Headlamp_Ctrl_PWR_LH (HSD11_1)
Headlamp_Relay_2_Ctrl (HB5A)
as requested by:
BLH_DippedBeamActivate_Req AND
BRH_DippedBeamActivate_Req during all times
- _Object type: Misuse Test
- _Status: REVIEWED
- _Procedure: Test Steps :
  BLH_DippedBeamActivate_Req
  BRH_DippedBeamActivate_Req
  during all NIgnitionStatus 0x05 when moniroting is not active
- _Pass criteria: Verify that :
  Headlamp_Ctrl_PWR_RH (HSD11_2)
  Headlamp_Ctrl_PWR_LH (HSD11_1
  Headlamp_Relay_2_Ctrl (HB5A)
- _Regression: No
- _Time [hr]: 0.1
- _Test environment: HIL (manual)

## STC-BDY02-1505: Main beam activation
The ExteriorLightingSafetyZa1 shall command
Headlamp_Relay_2_Ctrl (HB5A)
as requested by
BFrontLampPWRSupply_Req during all times
- _Object type: Misuse Test
- _Status: REVIEWED
- _Procedure: Test Steps :
  BFrontLampPWRSupply_Req
  during all NIgnitionStatus 0x05 when moniroting is not active
- _Pass criteria: Verify that :
  Headlamp_Relay_2_Ctrl (HB5A) as commanded
- _Regression: No
- _Time [hr]: 0.1
- _Test environment: Lab-Car (manual)

## STC-BDY02-1370: MasterLightSwitch in Dipped Beam On Status
The ExteriorLightingSafetyZa1 detect when all the below occur:
NMasterLightSwitchStatusFuSa = 0x4 (DIPPED BEAM ON)
BLH_DippedBeamActivate_Req = "no activation request"
BRH_DippedBeamActivate_Req = "no activation request"
NIgnitionStatus ==0x5 (Ignition)
within DTI = 100ms.
- _Object type: Misuse Test
- _Status: REVIEWED
- _Procedure: Test Steps :
  NMasterLightSwitchStatusFuSa = 0x4 (DIPPED BEAM ON) && BLH_DipperBeamActivate_Req = No activation request & BRH_DippedBeamActivate_Req = No activation request &&
  NIgnitionStatus ==0x5
- _Pass criteria: Verify that :
  Headlamp_Ctrl_PWR_RH (HSD11_2) = 100 % duty cycle command &&
  Headlamp_Ctrl_PWR_LH (HSD11_1) = 100% duty cycle && Headlamp_Relay_2_Ctrl (HB5A) = HIgh
- _Regression: No
- _Time [hr]: 0.1
- _Test environment: HIL (manual)

## STC-BDY02-1506: MasterLightSwitchFault in Active Status
The ExteriorLightingSafetyZa1 shall detect when all the below occur:
BMasterLightSwitchFaultStatusFuSa = Active
BLH_DippedBeamActivate_Req = "no activation request"
BRH_DippedBeamActivate_Req = "no activation request"
NIgnitionStatus ==0x5 (Ignition)
within DTI = 100ms.
- _Object type: Misuse Test
- _Status: REVIEWED
- _Procedure: Test Steps :
  BMasterLightSwitchFaultStatusFuSa = Active && BLH_DipperBeamActivate_Req = No activation request & BRH_DippedBeamActivate_Req = No activation request &&
  NIgnitionStatus ==0x5
- _Pass criteria: Verify that :
  Headlamp_Ctrl_PWR_RH (HSD11_2) = 100 % duty cycle command &&
  Headlamp_Ctrl_PWR_LH (HSD11_1) = 100% duty cycle
  Headlamp_Relay_2_Ctrl (HB5A) = HIgh
- _Regression: No
- _Time [hr]: 0.1
- _Test environment: HIL (manual)

## STC-BDY02-1507: Safe State #BDY02_FL_1
Upon detection of [STC-BDY02-1370] or [STC-BDY02-1506] the ExteriorLightingSafetyZa1 transition to Safe State #BDY02_FL_1.
- _Object type: Misuse Test
- _Status: REVIEWED
- _Procedure: Test Steps :
  NMasterLightSwitchStatusFuSa = 0x4 (DIPPED BEAM ON) && BLH_DipperBeamActivate_Req = No activation request & BRH_DippedBeamActivate_Req = No activation request
- _Pass criteria: Verify that :
  Headlamp_Ctrl_PWR_RH (HSD11_2) = 100 % duty cycle command &&
  Headlamp_Ctrl_PWR_LH (HSD11_1) = 100% duty cycle && Headlamp_Relay_2_Ctrl (HB5A) = HIgh
- _Regression: No
- _Time [hr]: 0.1
- _Test environment: HIL (manual)

## STC-BDY02-1508: Critical temperature threshold
No action is to be taken when DcuMonTemperatureSafetyMaskZa1 = Critical temperature threshold.
- _Object type: Misuse Test
- _Status: REVIEWED
- _Procedure: DcuMonTemperatureSafetyMaskZa1 = Critical temperature threshold.
- _Pass criteria: No reaction.
- _Regression: No
- _Time [hr]: 0.1
- _Test environment: HIL (manual)

## STC-BDY02-1371: High Side Command Headlamp with with max duty
Headlamp duty command
- _Object type: Misuse Test
- _Status: REVIEWED
- _Procedure: The ExteriorLightingSafetyZa1 command 100% duty cycle the outputs:
  Headlamp_Ctrl_PWR_RH (HSD11_2)
  Headlamp_Ctrl_PWR_LH (HSD11_1)
- _Pass criteria: Verify that both Headlamps are lighted on.
- _Regression: No
- _Time [hr]: 0.1
- _Test environment: HIL (manual)

## STC-BDY02-1509: High Side Command Headlamp with with relay
Headlamp relay command
- _Object type: Misuse Test
- _Status: REVIEWED
- _Procedure: The ExteriorLightingSafetyZa1 command "High side activated":
  Headlamp_Relay_2_Ctrl (HB5A)
- _Pass criteria: Verify that both Headlamps are lighted on.
- _Regression: No
- _Time [hr]: 0.1
- _Test environment: HIL (manual)

## STC-BDY02-1510: ElcSafety
ElcSafety command safety signals
- _Object type: Misuse Test
- _Status: REVIEWED
- _Procedure: The ElcSafety command the below signal:
  NFlcSafetyClusterMessage = "fault value"
  FlcSafetyStatusMask = TBD (specific fault detected i.e. short to gound, battery, open, etc.)
- _Pass criteria: Verify that both signal are activated.
- _Regression: No
- _Time [hr]: 0.1
- _Test environment: HIL (manual)

## STC-BDY02-1372: Safe State #BDY02_FL_1 Action
While in Safe State #BDY02_FL_1, the ExteriorLightingSafetyZa1 perform the action specified in [STC-BDY02-1371], [STC-BDY02-1509] within FRT = 100 ms.
- _Object type: Misuse Test
- _Status: REVIEWED
- _Procedure: Test Steps :
  Master Light switch status = Step4 && BLH_DipperBeamActivate_Req = No activation request & BRH_DipperBeamActivate_Req = No activation request
  HW failures (i.e. short to ground, open, short to battery, out of range) on the signal specified in [1334]
- _Pass criteria: Verify that Dipped Beam is activated.
- _Regression: No
- _Time [hr]: 0.1
- _Test environment: HIL (manual)

## STC-BDY02-1511: Safe State #BDY02_FL_1 exit condition
The ExteriorLightingSafetyZa1 exit Safe State #BDY02_FL_1 at the new vehicle ignition cycle or after a healing time interval, HTI= 3 secs, when the fault no longer exists.
- _Object type: Misuse Test
- _Status: REVIEWED
- _Procedure: Next Ignition Cycle OR HTI=3s
- _Pass criteria: Verify that exit Safe State #BDY02_2 and Normal Operation of ElcSafety.
- _Regression: No
- _Time [hr]: 0.1
- _Test environment: HIL (manual)

## STC-BDY02-1374: Safe State #BDY02_FL_2 Action
While in Safe State #BDY02_FL_2 , the ExteriorLightingSafetyZa1 perform the action specified in [STC-BDY02-1510] within FRT = 100 ms.
- _Object type: Misuse Test
- _Status: REVIEWED
- _Procedure: Test Steps :
  HW failures (i.e. short to ground, open, short to battery, out of range) on the signal specified in [1341] OR
  No command to activate Dipped beam
- _Pass criteria: Verify that the warning sent to driver.
- _Regression: No
- _Time [hr]: 0.1
- _Test environment: HIL (manual)

## STC-BDY02-1376: Safe State #BDY02_FL_2 exit condition
The ExteriorLightingSafetyZa1 exit Safe State #BDY02_FL_2 at the new vehicle ignition cycle or after a healing time interval, HTI= 3 secs, when the fault no longer exists.
- _Object type: Misuse Test
- _Status: REVIEWED
- _Procedure: Next Ignition Cycle OR HTI=3s
- _Pass criteria: Verify that exit Safe State #BDY02_3 and Normal Operation of ElcSafety.
- _Regression: No
- _Time [hr]: 0.1
- _Test environment: HIL (manual)

## STC-BDY02-1515: Safe State #BDY02_FL_3 Action
While in Safe State #BDY02_FL_3 , the ExteriorLightingSafetyZa1 perform the action specified in [STC-BDY02-1510] within FRT = 100 ms.
- _Object type: Misuse Test
- _Status: REVIEWED
- _Procedure: Test Steps :
  HW failures (i.e. short to ground, open, short to battery, out of range) on the signal specified in [1341] OR
  No command to activate Dipped beam
- _Pass criteria: Verify that the warning sent to driver and request of emergency activation to ZB1.
- _Regression: No
- _Time [hr]: 0.1
- _Test environment: HIL (manual)

## STC-BDY02-1517: Safe State #BDY02_FL_3 exit condition
The ExteriorLightingSafetyZa1 exit Safe State #BDY02_FL_3 at the new vehicle ignition cycle or after a healing time interval, HTI= 3 secs, when the fault no longer exists.
- _Object type: Misuse Test
- _Status: REVIEWED
- _Procedure: Next Ignition Cycle OR HTI=3s
- _Pass criteria: Verify that exit Safe State #BDY02_3 and Normal Operation of ElcSafety.
- _Regression: No
- _Time [hr]: 0.1
- _Test environment: HIL (manual)

## STC-BDY02-1381: ExteriorLightingSafetyZa1 signal received
Signal received check
- _Object type: Misuse Test
- _Status: REVIEWED
- _Procedure: The ExteriorLightingSafetyZa1 receive the following signals:
  NMasterLightSwitchStatusFuSa
  BMasterLightSwitchFaultStatusFuSa
  EflcSafetyStatusMask
  BLH_DippedBeamActivate_Req
  BRH_DippedBeamActivate_Req
  Headlamp_PWR_Status_RH (DI2)
  Headlamp_PWR_Status_LH (DI1)
  DcuMonTemperatureSafetyMaskZa1
  NIgnitionStatus
  BFrontLampPWRSupply_Req
- _Pass criteria: Verify that ExteriorLightingSafetyZa1 receive all signals.
  The message containing the signals :
  NMasterLightSwitchStatusFuSa
  BMasterLightSwitchFaultStatusFuSa
  EflcSafetyStatusMask
  NIgnitionStatus
  is protected with E2E.
- _Regression: No
- _Time [hr]: 0.1
- _Test environment: HIL (manual)

## STC-BDY02-1384: No activation command to activate dipped beam on driver request
The ExteriorLightingSafetyZa1 detect the following:
Headlamp_Relay_2_Ctrl (HB5A) is commanded "High side activated"; AND
any of the signal specified in [1336] is read LOW
within DTI = 200ms.
- _Object type: Misuse Test
- _Status: REVIEWED
- _Procedure: No activation command to activate dipped beam on driver request. Either of the signals below is read LOW :
  Headlamp_PWR_Status_RH (DI2)
  Headlamp_PWR_Status_LH (DI1)
- _Pass criteria: Verify that the warning sent to driver.
- _Regression: No
- _Time [hr]: 0.1
- _Test environment: HIL (manual)

## STC-BDY02-1518: Status of head lamp activation command detected
Upon detection of [STC-BDY02-1384], the ExteriorLightingSafetyZa1 transition to Safe State #BDY02_FL_2.
- _Object type: Misuse Test
- _Status: REVIEWED
- _Procedure: Status of head lamp activation command detected LOW :
  Either of the signals below is read LOW :
  Headlamp_PWR_Status_RH (DI2)
  Headlamp_PWR_Status_LH (DI1)
- _Pass criteria: Verify that the warning sent to driver.
- _Regression: No
- _Time [hr]: 0.1
- _Test environment: HIL (manual)

## STC-BDY02-1519: Dipped Beam activation
The ExteriorLightingSafetyZa1 detect a communication error in the signal [1334] within DTI = 200ms.
- _Object type: Misuse Test
- _Status: REVIEWED
- _Procedure: Communication error.
- _Pass criteria: Verify that the Dipped Beam is activated.
  within DTI = 200ms.
- _Regression: No
- _Time [hr]: 0.1
- _Test environment: HIL (manual)

## STC-BDY02-1520: Safe State #BDY02_FL_1
Upon detection of [STC-BDY02-1519], the ExteriorLightingSafetyZa1 transition to Safe State #BDY02_FL_1.
- _Object type: Misuse Test
- _Status: REVIEWED
- _Procedure: Communication error.
- _Pass criteria: Verify that the Dipped Beam is activated.
- _Regression: No
- _Time [hr]: 0.1
- _Test environment: HIL (manual)

## STC-BDY02-1521: Communication error on many signals
The ExteriorLightingSafetyZa1 detect a communication error in the signal NignitionStatus AND NMasterLightSwitchStatusFuSa=0X4 OR BMasterLightSwitchFaultStatusFuSa = Active, within DTI = 200ms.
- _Object type: Misuse Test
- _Status: REVIEWED
- _Procedure: Communication error on NignitionStatus.
- _Pass criteria: Verify that the Dipped Beam is activated.
  within DTI = 200ms.
- _Regression: No
- _Time [hr]: 0.1
- _Test environment: HIL (manual)

## STC-BDY02-1522: Safe State #BDY02_FL_1
Upon detection of [STC-BDY02-1521], the ExteriorLightingSafetyZa1 transition to Safe State #BDY02_FL_1.
- _Object type: Misuse Test
- _Status: REVIEWED
- _Procedure: Communication error on NignitionStatus.
- _Pass criteria: Verify that the Dipped Beam is activated.
- _Regression: No
- _Time [hr]: 0.1
- _Test environment: HIL (manual)

## STC-BDY02-1523: E2E protection 1
Signals Check
- _Object type: Misuse Test
- _Status: REVIEWED
- _Procedure: The ExteriorLightingSafetyZa1 command the following signals:
  Headlamp_Relay_2_Ctrl (HB5A)
  Headlamp_Ctrl_PWR_RH (HSD11_2)
  Headlamp_Ctrl_PWR_LH (HSD11_1)
  FlcSafetyStatusMask
- _Pass criteria: Verify that the message containing the signal specified is protected with an E2E protection mechanism.
- _Regression: No
- _Time [hr]: 0.1
- _Test environment: HIL (manual)

## STC-BDY02-1525: E2E protection 2
Signal Check
- _Object type: Misuse Test
- _Status: REVIEWED
- _Procedure: The ExteriorLightingSafetyZa1 output a 32-bits signal called FlcSafetyStatusMask to communicate to the Elc (QM SWC) and ExteriorLightingSafetyZb1 the faults status.
- _Pass criteria: Verify that the message containing the signal specified is protected with an E2E protection mechanism.
- _Regression: No
- _Time [hr]: 0.1
- _Test environment: HIL (manual)

## STC-BDY02-1524: HW failures on Headlamp_Relay_2_Ctrl
The ExteriorLightingSafetyZa1 detect HW failures (i.e. short to ground, open, short to battery, out of range) on the signal Headlamp_Relay_2_Ctrl (HB5A) within DTI = 200ms.
- _Object type: Misuse Test
- _Status: REVIEWED
- _Procedure: HW fault on :
  Headlamp_Relay_2_Ctrl (HB5A)
- _Pass criteria: Verify that the warning sent to driver
  ZB1 activate the front light only in case of open circuit.
- _Regression: No
- _Time [hr]: 0.1
- _Test environment: HIL (manual)

## STC-BDY02-1526: Safe State #BDY02_FL_3
Upon detection of [STC-BDY02-1524], the ExteriorLightingSafetyZa1 transition to Safe State #BDY02_FL_3.
- _Object type: Misuse Test
- _Status: REVIEWED
- _Procedure: HW fault on :
  Headlamp_Relay_2_Ctrl (HB5A)
- _Pass criteria: Verify that the warning sent to driver
  ZB1 activate the front light only in case of open circuit.
- _Regression: No
- _Time [hr]: 0.1
- _Test environment: HIL (manual)

## STC-BDY02-1527: HW failures on Headlamp_Ctrl_PWR_RH and Headlamp_Ctrl_PWR_LH
The ExteriorLightingSafetyZa1 detect HW failures (i.e. short to ground, open, short to battery, out of range) on the signals Headlamp_Ctrl_PWR_RH (HSD11_2) and
Headlamp_Ctrl_PWR_LH (HSD11_1) within DTI = 200ms.
- _Object type: Misuse Test
- _Status: REVIEWED
- _Procedure: HW fault on :
  Headlamp_Ctrl_PWR_RH (HSD11_2
  Headlamp_Ctrl_PWR_LH (HSD11_1)
- _Pass criteria: Verify that the warning sent to driver.
- _Regression: No
- _Time [hr]: 0.1
- _Test environment: HIL (manual)

## STC-BDY02-1528: Safe State #BDY02_FL_2
Upon detection of [STC-BDY02-1527], the ExteriorLightingSafetyZa1 shall transition to Safe State #BDY02_FL_2.
- _Object type: Misuse Test
- _Status: REVIEWED
- _Procedure: HW fault on :
  Headlamp_Ctrl_PWR_RH (HSD11_2
  Headlamp_Ctrl_PWR_LH (HSD11_1)
- _Pass criteria: Verify that the warning sent to driver.
- _Regression: No
- _Time [hr]: 0.1
- _Test environment: HIL (manual)

## STC-BDY02-1387: SW Composition ExteriorLightingSafetyZb2
Composition Check
- _Object type: Misuse Test
- _Status: REVIEWED
- _Procedure: The SW composition ExteriorLightingSafetyZb2 implementing the safety monitoring of this function is designed.
- _Pass criteria: Verify that the SW composition is connected to the actuations of the outputs.
- _Regression: No
- _Time [hr]: 0.1
- _Test environment: HIL (manual)

## STC-BDY02-1390: FlcSafetyStatusMask in fault
Command Check
- _Object type: Misuse Test
- _Status: REVIEWED
- _Procedure: When the signal FlcSafetyStatusMask == "open circuit fault"
- _Pass criteria: The ExteriorLightingSafetyZb1 command:
  Headlamp_Relay_2_Ctrl2 (HSD9_1) = "High side activated"
  EflcSafetyStatusMask = bit 1
- _Regression: No
- _Time [hr]: 0.1
- _Test environment: HIL (manual)

## STC-BDY02-1530: NMasterLightSwitchStatusFuSa value
Master Light Switch Resistor Ladder 1 Voltage
- _Object type: Misuse Test
- _Status: REVIEWED
- _Procedure: The ExteriorLightingSafetyZb1 set the signal NMasterLightSwitchStatusFuSa values accordingly with the voltage of the input signal Master Light Switch Resistor Ladder 1 (AN14_PI2).
- _Pass criteria: Verify that the voltage is as for table [1394] and check NMasterLightSwitchStatus.
- _Regression: No
- _Time [hr]: 0.1
- _Test environment: HIL (manual)

## STC-BDY02-1573: Critical temperature threshold
No action is to be taken when DcuMonTemperatureSafetyMaskZb1 = Critical temperature threshold.
- _Object type: Misuse Test
- _Status: REVIEWED
- _Procedure: DcuMonTemperatureSafetyMaskZb1 = Critical temperature threshold
- _Pass criteria: No reaction
- _Regression: No
- _Time [hr]: 0.1
- _Test environment: HIL (manual)

## STC-BDY02-1531: Input Interfaces
Signal Check
- _Object type: Misuse Test
- _Status: REVIEWED
- _Procedure: The ExteriorLightingSafetyZb1 receive the following signals from the ExteriorLightingSafetyZa1:
  FlcSafetyStatusMask
- _Pass criteria: Make Sure ExteriorLightingSafetyZb1 is receiving following signals
  FlcSafetyStatusMask
  Verify that the message containing the signal is protected with appropriate E2E mechanism.
- _Regression: No
- _Time [hr]: 0.1
- _Test environment: Lab-Car (manual)

## STC-BDY02-1533: Input Interfaces
Signals Check
- _Object type: Misuse Test
- _Status: REVIEWED
- _Procedure: The ExteriorLightingSafetyZb1 receive the following signals:
  Master Light Switch Resistor Ladder 1 (AN14_PI2)
  DcuMonTemperatureSafetyMaskZb1
  NIgnitionStatus
- _Pass criteria: Make Sure ExteriorLightingSafetyZb1 is receiving following signals
  Master Light Switch Resistor Ladder 1 (AN14_PI2)
  DcuMonTemperatureSafetyMaskZb1
  NIgnitionStatus
- _Regression: No
- _Time [hr]: 0.1
- _Test environment: Lab-Car (manual)

## STC-BDY02-1393: HW failures BMasterLightSwitchFaultStatusFuSa (OC)
The ExteriorLightingSafetyZb1 detect HW failures (i.e. short to ground, open, short to battery, out of range) on the signal BMasterLightSwitchFaultStatusFuSa within DTI = 200ms.
- _Object type: Misuse Test
- _Status: REVIEWED
- _Procedure: HW failures (i.e. short to ground, open, short to battery, out of range) on Master LIght Switch
- _Pass criteria: Verify that BMasterLightSwitchFaultStatusFuSa = active
- _Regression: No
- _Time [hr]: 0.1
- _Test environment: HIL (manual)

## STC-BDY02-1534: HW failures BMasterLightSwitchFaultStatusFuSa (OOR)
The ExteriorLightingSafetyZb1 detect when the singal BMasterLightSwitchFaultStatusFuSa falls out of the valid ranges as defined in [1394] DTI = 200ms.
- _Object type: Misuse Test
- _Status: REVIEWED
- _Procedure: Out of range
- _Pass criteria: Verify that BMasterLightSwitchFaultStatusFuSa = active
- _Regression: No
- _Time [hr]: 0.1
- _Test environment: HIL (manual)

## STC-BDY02-1535: BMasterLightSwitchFaultStatusFuSa Status
Upon detection of [1339] or [1726], the ExteriorLightingSafetyZb1 set BMasterLightSwitchFaultStatusFuSa to Active wihtin FRT = 100ms.
- _Object type: Misuse Test
- _Status: REVIEWED
- _Procedure: HW failures (i.e. short to ground, open, short to battery, out of range) or out of range
- _Pass criteria: Verify that BMasterLightSwitchFaultStatusFuSa = active within FRT =100ms and EflcSafetyStatusMask = bit2 to 3
- _Regression: No
- _Time [hr]: 0.1
- _Test environment: HIL (manual)

## STC-BDY02-1532: Command Signal
Signal Check
- _Object type: Misuse Test
- _Status: REVIEWED
- _Procedure: The ExteriorLightingSafetyZb1 command the following signals:
  Headlamp_Relay_2_Ctrl2 (HSD9_1)
- _Pass criteria: Verify that the ExteriorLightingSafetyZb1 command the signal.
- _Regression: No
- _Time [hr]: 0.1
- _Test environment: HIL (manual)

## STC-BDY02-1536: E2E Protection 1
Signals Check
- _Object type: Misuse Test
- _Status: REVIEWED
- _Procedure: The ExteriorLightingSafetyZb1 command the following signals to the ExteriorLightingSafetyZa1 and ExteriorLightingSafetyZc1:
  EflcSafetyStatusMask
  NMasterLightSwitchStatusFuSa
  BMasterLightSwitchFaultStatusFuSa
- _Pass criteria: Verify that the ExteriorLightingSafetyZb1 command the signals and that the message containing the signal specified EflcSafetyStatusMask is protected with an E2E protection mechanism.
- _Regression: No
- _Time [hr]: 0.1
- _Test environment: HIL (manual)

## STC-BDY02-1396: HW Fault on Headlamp_Relay_2_Ctrl
The ExteriorLightingSafetyZb1 detect HW failures (i.e. short to ground, open, short to battery, out of range) on the signal Headlamp_Relay_2_Ctrl within DTI = 200ms.
- _Object type: Misuse Test
- _Status: REVIEWED
- _Procedure: HW Fault on Headlamp_Relay_2_Ctrl (HB5A)
- _Pass criteria: Verify that EflcSafetyStatusMask = bit 4 to 7
- _Regression: No
- _Time [hr]: 0.1
- _Test environment: HIL (manual)

## STC-BDY02-1538: HW Fault on Headlamp_Relay_2_Ctrl
Upon detection of [STC-BDY02-1396], the ExteriorLightingSafetyZb1 set EflcSafetyStatusMask = bit 4 to 7 wihtin FRT = 100ms
- _Object type: Misuse Test
- _Status: REVIEWED
- _Procedure: HW Fault on Headlamp_Relay_2_Ctrl (HB5A)
- _Pass criteria: Verify that EflcSafetyStatusMask = bit 4 to 7
- _Regression: No
- _Time [hr]: 0.1
- _Test environment: HIL (manual)

## STC-BDY02-1399: SW Composition ExteriorLightingSafetyZc1
Composition Check
- _Object type: Misuse Test
- _Status: REVIEWED
- _Procedure: The SW composition ExteriorLightingSafetyZc1 implementing the safety monitoring of this function is designed.
- _Pass criteria: Verify that the SW composition is the only connected to the actuations of the outputs.
- _Regression: No
- _Time [hr]: 0.1
- _Test environment: HIL (manual)

## STC-BDY02-1539: SW Composition Brake/Tail Light Contro
Composition Check
- _Object type: Misuse Test
- _Status: REVIEWED
- _Procedure: The SW composition Brake/Tail Light Control is defined.
- _Pass criteria: Verify that the compositions Master Light Control is not connected to any actuation of the outputs.
- _Regression: No
- _Time [hr]: 0.1
- _Test environment: HIL (manual)

## STC-BDY02-1402: Stop Tail Command
Command Check
- _Object type: Misuse Test
- _Status: REVIEWED
- _Procedure: The ExteriorLightingSafetyZc1 command
  Stop_Tail_Outboard_PWR_RH (HSD3)
  Stop_Tail_Inboard_PWR_RH (HSD4)
  Stop_Tail_Outboard_PWR_LH (HSD8)
  Stop_Tail_Inboard_PWR_LH (HSD7)
  as requested by
  NLHTailInboardLampActivate_Req
  NLHTailOutboardLampActivate_Req
  NRHTailInboardLampActivate_Req
  NRHTailOutboardLampActivate_Req
- _Pass criteria: Verify that the command is at all times.
- _Regression: No
- _Time [hr]: 0.1
- _Test environment: HIL (manual)

## STC-BDY02-1540: BrakeLightConditionHappen Status 1
The ExteriorLightingSafetyZc1 set BrakeLightConditionHappen to true when either of the following occurs:
Brake Pedal is pressed (NBrakepedalStatus_Q == Valid && NBrakepedalStatus == Pressed)
Deceleration is above LongActiveThreshold calibratable ( gLongitudinal < -1.3 m/s2 only && gLongitudinal_Q = Valid)
- _Object type: Misuse Test
- _Status: REVIEWED
- _Procedure: Test Steps :
  NBrakepedalStatus_Q == Valid && NBrakepedalStatus == Pressed
  NgLongitudinal_Q == Valid && gLongitudinal < -1.3 m/s2
- _Pass criteria: Verify that BrakeLightConditionHappen =True.
- _Regression: No
- _Time [hr]: 0.1
- _Test environment: HIL (manual)

## STC-BDY02-1541: BrakeLightConditionHappen Status 2
The ExteriorLightingSafetyZc1 shall set BrakeLightConditionHappen to true when all the following occurs:
NBrakepedalStatus_Q != Valid
NpBrake_Q == Valid
pBrake > pBrakeThresholdActive
- _Object type: Misuse Test
- _Status: REVIEWED
- _Procedure: NBrakepedalStatus_Q != Valid && NpBrake_Q == Valid && pBrake >= pBrakeThresholdActive
- _Pass criteria: Verify that BrakeLightConditionHappen =True.
- _Regression: No
- _Time [hr]: 0.1
- _Test environment: HIL (manual)

## STC-BDY02-1542: Stop Tail Duty Cycle
Lamp Intensity Check
- _Object type: Misuse Test
- _Status: REVIEWED
- _Procedure: The ExteriorLightingSafetyZc1 set the duty cycle of the outputs :
  Stop_Tail_Outboard_PWR_RH (HSD3)
  Stop_Tail_Inboard_PWR_RH (HSD4)
  Stop_Tail_Outboard_PWR_LH (HSD8)
  Stop_Tail_Inboard_PWR_LH (HSD7)
  as requested by
  NTailInboardLampIntensity_Req
  NTailOutboardLampIntensity_Req
- _Pass criteria: Verify that the command is at all times.
- _Regression: No
- _Time [hr]: 0.1
- _Test environment: HIL (manual)

## STC-BDY02-1404: Command Brake Light 1
The ExteriorLightingSafetyZc1 detect when:
BrakeLightConditionHappen is set to true;
AND
NLHTailInboardLampActivate_Req = 'no request' AND
NLHTailOutboardLampActivate_Req = 'no request' AND
NRHTailInboardLampActivate_Req = 'no request' AND
NRHTailOutboardLampActivate_Req = 'no request'; AND
NIgnitionStatus ==0x5 (Ignition)
within DTI = 100ms.
- _Object type: Misuse Test
- _Status: REVIEWED
- _Procedure: Test Steps :
  BrakeLightConditionHappen is set to true
  NLHTailInboardLampActivate_Req = 'no request'
  NLHTailOutboardLampActivate_Req = 'no request'
  NRHTailInboardLampActivate_Req = 'no request'
  NRHTailOutboardLampActivate_Req = 'no request'
  NIgnitionStatus ==0x5 (Ignition)
  within DTI = 100ms.
- _Pass criteria: Verify that the Command brake light :
  Stop_Tail_Outboard_PWR_RH (HSD3)
  Stop_Tail_Inboard_PWR_RH (HSD4)
  Stop_Tail_Outboard_PWR_LH (HSD8)
  Stop_Tail_Inboard_PWR_LH (HSD7)
- _Regression: No
- _Time [hr]: 0.1
- _Test environment: HIL (manual)

## STC-BDY02-1543: Safe State #BDY02_RL_1
Upon detection of [STC-BDY02-1404] the ExteriorLightingSafetyZc1 transition to Safe State #BDY02_RL_1.
- _Object type: Misuse Test
- _Status: REVIEWED
- _Procedure: Test Steps :
  BrakeLightConditionHappen is set to true
  NLHTailInboardLampActivate_Req = 'no request'
  NLHTailOutboardLampActivate_Req = 'no request'
  NRHTailInboardLampActivate_Req = 'no request'
  NRHTailOutboardLampActivate_Req = 'no request'
  NIgnitionStatus ==0x5 (Ignition)
  within DTI = 100ms.
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)
- _Regression: No
- _Time [hr]: 0.1
- _Test environment: HIL (manual)

## STC-BDY02-1544: Command Brake Light 2
The ExteriorLightingSafetyZc1 detect when:
NMasterLightSwitchStatusFuSa != 0x0 (OFF)
AND
BrakeLightConditionHappen is set false AND
NLHTailInboardLampActivate_Req = 'no request' AND
NLHTailOutboardLampActivate_Req = 'no request' AND
NRHTailInboardLampActivate_Req = 'no request' AND
NRHTailOutboardLampActivate_Req = 'no request'; AND
NIgnitionStatus ==0x5 (Ignition)
within DTI = 100ms.
- _Object type: Misuse Test
- _Status: REVIEWED
- _Procedure: Test Steps :
  NMasterLightSwitchStatusFuSa != 0x0 (OFF)
  BrakeLightCondition is set false
  NLHTailInboardLampActivate_Req = 'no request'
  NLHTailOutboardLampActivate_Req = 'no request'
  NRHTailInboardLampActivate_Req = 'no request'
  NRHTailOutboardLampActivate_Req = 'no request'
  NIgnitionStatus ==0x5 (Ignition)
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)
  within 100ms
- _Regression: No
- _Time [hr]: 0.1
- _Test environment: HIL (manual)

## STC-BDY02-1545: Command Brake Light 3
The ExteriorLightingSafetyZc1 detect when:
BMasterLightSwitchFaultStatusFuSa = 0x1 (TRUE STATE meaning ACTIVE FAULT)
AND
BrakeLightConditionHappen is set false AND
NLHTailInboardLampActivate_Req = 'no request' AND
NLHTailOutboardLampActivate_Req = 'no request' AND
NRHTailInboardLampActivate_Req = 'no request' AND
NRHTailOutboardLampActivate_Req = 'no request';AND
NIgnitionStatus ==0x5 (Ignition)
within DTI = 100ms.
- _Object type: Misuse Test
- _Status: REVIEWED
- _Procedure: Test Steps :
  BMasterLightSwitchFaultStatusFuSa = Active
  BrakeLightCondition is set false
  NLHTailInboardLampActivate_Req = 'no request'
  NLHTailOutboardLampActivate_Req = 'no request'
  NRHTailInboardLampActivate_Req = 'no request'
  NRHTailOutboardLampActivate_Req = 'no request'
  NIgnitionStatus ==0x5 (Ignition)
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)
  within 100ms
- _Regression: No
- _Time [hr]: 0.1
- _Test environment: HIL (manual)

## STC-BDY02-1546: Safe State #BDY02_RL_2
Upon detection of [STC-BDY02-1544] or [STC-BDY02-1545] the ExteriorLightingSafetyZc1 transition to Safe State #BDY02_RL_2.
- _Object type: Misuse Test
- _Status: REVIEWED
- _Procedure: Test Steps :
  BMasterLightSwitchFaultStatusFuSa = Active
  BrakeLightCondition is set false
  NLHTailInboardLampActivate_Req = 'no request'
  NLHTailOutboardLampActivate_Req = 'no request'
  NRHTailInboardLampActivate_Req = 'no request'
  NRHTailOutboardLampActivate_Req = 'no request'
  NIgnitionStatus ==0x5 (Ignition)
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)
- _Regression: No
- _Time [hr]: 0.1
- _Test environment: HIL (manual)

## STC-BDY02-1547: Command Brake Light 4 (88%)
The ExteriorLightingSafetyZc1 detect when:
BMasterLightSwitchFaultStatusFuSa = 0x1 (TRUE STATE meaning ACTIVE FAULT) OR NMasterLightSwitchStatusFuSa != 0x0 (OFF) AND
(NTailInboardLampIntensity_Req <65% OR NTailInboardLampIntensity_Req <65%) AND
NIgnitionStatus ==0x5 (Ignition)
within DTI = 100ms.
- _Object type: Misuse Test
- _Status: REVIEWED
- _Procedure: Rear Light request active
- _Pass criteria: Verify that the Command 88% :
  Stop_Tail_Outboard_PWR_RH (HSD3)
  Stop_Tail_Inboard_PWR_RH (HSD4)
  Stop_Tail_Outboard_PWR_LH (HSD8
  Stop_Tail_Inboard_PWR_LH (HSD7)
  within 100ms
- _Regression: No
- _Time [hr]: 0.1
- _Test environment: HIL (manual)

## STC-BDY02-1548: Safe State #BDY02_RL_2
Upon detection of [STC-BDY02-1544] or [STC-BDY02-1545] the ExteriorLightingSafetyZc1 transition to Safe State #BDY02_RL_2.
- _Object type: Misuse Test
- _Status: REVIEWED
- _Procedure: Rear Light request active
- _Pass criteria: Verify that the Command 88% :
  Stop_Tail_Outboard_PWR_RH (HSD3)
  Stop_Tail_Inboard_PWR_RH (HSD4)
  Stop_Tail_Outboard_PWR_LH (HSD8
  Stop_Tail_Inboard_PWR_LH (HSD7)
- _Regression: No
- _Time [hr]: 0.1
- _Test environment: HIL (manual)

## STC-BDY02-1549: Command Brake Light 5 (100%)
The ExteriorLightingSafetyZc1 detect when:
BrakeLightConditionHappen is set TRUE AND
(NTailInboardLampIntensity_Req <65% OR NTailOutboardLampIntensity_Req <65%)
within DTI = 100ms.
- _Object type: Misuse Test
- _Status: REVIEWED
- _Procedure: Brake Light condition is true
- _Pass criteria: Verify that the Command 100% :
  Stop_Tail_Outboard_PWR_RH (HSD3)
  Stop_Tail_Inboard_PWR_RH (HSD4)
  Stop_Tail_Outboard_PWR_LH (HSD8
  Stop_Tail_Inboard_PWR_LH (HSD7)
  within 100ms
- _Regression: No
- _Time [hr]: 0.1
- _Test environment: HIL (manual)

## STC-BDY02-1550: Safe State #BDY02_RL_1
Upon detection of [STC-BDY02-1544] or [STC-BDY02-1545] the ExteriorLightingSafetyZc1 transition to Safe State #BDY02_RL_1.
- _Object type: Misuse Test
- _Status: REVIEWED
- _Procedure: Brake Light condition is true
- _Pass criteria: Verify that the Command 100% :
  Stop_Tail_Outboard_PWR_RH (HSD3)
  Stop_Tail_Inboard_PWR_RH (HSD4)
  Stop_Tail_Outboard_PWR_LH (HSD8
  Stop_Tail_Inboard_PWR_LH (HSD7)
- _Regression: No
- _Time [hr]: 0.1
- _Test environment: HIL (manual)

## STC-BDY02-1551: No reaction with critical temperature
No action is to be taken when DcuMonTemperatureSafetyMaskZc1 = Critical temperature threshold.
- _Object type: Misuse Test
- _Status: REVIEWED
- _Procedure: DcuMonTemperatureSafetyMaskZC1 = Critical temperature
- _Pass criteria: No reaction
- _Regression: No
- _Time [hr]: 0.1
- _Test environment: HIL (manual)

## STC-BDY02-1407: High Side Command Stop Tail Light with with 100% duty
Stop Tail Light command
- _Object type: Misuse Test
- _Status: REVIEWED
- _Procedure: The ExteriorLightingSafetyZc1 command 100% the outputs:
  Stop_Tail_Outboard_PWR_RH (HSD3)
  Stop_Tail_Inboard_PWR_RH (HSD4)
  Stop_Tail_Outboard_PWR_LH (HSD8)
  Stop_Tail_Inboard_PWR_LH (HSD7)
- _Pass criteria: Verify that Stop Tail Light are commanded.
- _Regression: No
- _Time [hr]: 0.1
- _Test environment: HIL (manual)

## STC-BDY02-1552: High Side Command Stop Tail Light with with 88% duty
- _Object type: Misuse Test
- _Status: REVIEWED
- _Procedure: The ExteriorLightingSafetyZc1 command 88% the outputs:
  Stop_Tail_Outboard_PWR_RH (HSD3)
  Stop_Tail_Inboard_PWR_RH (HSD4)
  Stop_Tail_Outboard_PWR_LH (HSD8)
  Stop_Tail_Inboard_PWR_LH (HSD7)
- _Pass criteria: Verify that Stop Tail Light are commanded.
- _Regression: No
- _Time [hr]: 0.1
- _Test environment: HIL (manual)

## STC-BDY02-1553: NRlcSafetyClusterMessage Fault
Signal Check
- _Object type: Misuse Test
- _Status: REVIEWED
- _Procedure: The ExteriorLightingSafetyZc1 command the below signal:
  NRlcSafetyClusterMessage = "fault value"
- _Pass criteria: Verify that the signal is in fault.
- _Regression: No
- _Time [hr]: 0.1
- _Test environment: HIL (manual)

## STC-BDY02-1410: Brake Light request
While in Safe State #BDY02_RL_1, the ExteriorLightingSafetyZc1 perform the action specified in [1648] within FRT = 100 ms.
- _Object type: Misuse Test
- _Status: REVIEWED
- _Procedure: Test Steps :
  BrakeLightConditionHappen is set to true;
  &&
  NRHTailLampActivate_Req =no request; &&
  NLHTailLampActivate_Req = norequest;
  OR
  Communication Error on any of the below signals :
  - NBrakePedalSwitch1Status
  NBrakePedalSwitch2Status
  pBrake
  gLongitudinal
  NgLongitudinal_Q
- _Pass criteria: Verify the Brake Light requested.
  within 100ms
- _Regression: No
- _Time [hr]: 0.1
- _Test environment: HIL (manual)

## STC-BDY02-1554: Exit Safe State #BDY02_1
The ExteriorLightingSafetyZc1 exit Safe State #BDY02_RL_1 at the new vehicle ignition cycle or after a healing time interval, HTI= 3 secs, when the fault no longer exists.
- _Object type: Misuse Test
- _Status: REVIEWED
- _Procedure: Next ignition cycle
- _Pass criteria: Verify the Exit Safe State #BDY02_1 and Normal Operation of ElcSafety.
- _Regression: No
- _Time [hr]: 0.1
- _Test environment: HIL (manual)

## STC-BDY02-1555: Tail light activation
While in Safe State #BDY02_RL_2, the ExteriorLightingSafetyZc1 perform the action specified in [1649] within FRT = 100 ms.
- _Object type: Misuse Test
- _Status: REVIEWED
- _Procedure: Test Steps :
  Master Light switch status = Step4 && BLH_DipperBeamActivate_Req = No activation request & BRH_DippedBeamActivate_Req = No activation request
  HW failures (i.e. short to ground, open, short to battery, out of range) on the signal specified in [1334]
- _Pass criteria: Verify the tail light activated
  within 100ms
- _Regression: No
- _Time [hr]: 0.1
- _Test environment: HIL (manual)

## STC-BDY02-1413: Exit Safe State #BDY02_2
The ExteriorLightingSafetyZc1 exit Safe State #BDY02_RL_2 at the new vehicle ignition cycle or after a healing time interval, HTI= 3 secs, when the fault no longer exists.
- _Object type: Misuse Test
- _Status: REVIEWED
- _Procedure: Next Ignition Cycle
- _Pass criteria: Verify the Exit Safe State #BDY02_2 and Normal Operation of ElcSafety
- _Regression: No
- _Time [hr]: 0.1
- _Test environment: HIL (manual)

## STC-BDY02-1556: Brake Light/Tail Ligt warning
While in Safe State #BDY02_RL_3, the ExteriorLightingSafetyZc1 perform the action specified in [1653] within FRT = 100 ms.
- _Object type: Misuse Test
- _Status: REVIEWED
- _Procedure: HW Fault in :
  Stop_Tail_Outboard_PWR_RH (HSD3)
  Stop_Tail_Inboard_PWR_RH (HSD4)
  Stop_Tail_Outboard_PWR_LH (HSD8)
  Stop_Tail_Inboard_PWR_LH (HSD7)
- _Pass criteria: Verify the Warning sent to driver (Brake Light/Tail Ligt warning)
  within 100ms
- _Regression: No
- _Time [hr]: 0.1
- _Test environment: HIL (manual)

## STC-BDY02-1416: Exit Safe State #BDY02_4
The ExteriorLightingSafetyZc1 exit Safe State #BDY02_RL_3 at the new vehicle ignition cycle or after a healing time interval, HTI= 3 secs, when the fault no longer exists.
- _Object type: Misuse Test
- _Status: REVIEWED
- _Procedure: Next Ignition Cycle
- _Pass criteria: Exit Safe State #BDY02_4 and Normal Operation of ElcSafety
- _Regression: No
- _Time [hr]: 0.1
- _Test environment: HIL (manual)

## STC-BDY02-1557: E2E Protection for input signals 1
Signals Check
- _Object type: Misuse Test
- _Status: REVIEWED
- _Procedure: The ExteriorLightingSafetyZc1 receive the following signals:
  NBrakePedalStatus
  NBrakePedalStatus_Q
  pBrake
  pBrake_Q
  gLongitudinal
  NgLongitudinal_Q
- _Pass criteria: Verify that the message containing the signals is protected with an E2E protection mechanism.
- _Regression: No
- _Time [hr]: 0.1
- _Test environment: HIL (manual)

## STC-BDY02-1558: Request Received Signals
Signals Check
- _Object type: Misuse Test
- _Status: REVIEWED
- _Procedure: The ExteriorLightingSafetyZc1 receive the following signals:
  NLHTailInboardLampActivate_Req
  NLHTailOutboardLampActivate_Req
  NRHTailInboardLampActivate_Req
  NRHTailOutboardLampActivate_Req
  NTailInboardLampIntensity_Req
  NTailOutboardLampIntensity_Req
  DcuMonTemperatureSafetyMaskZc1
- _Pass criteria: Verify that the request signals are received.
- _Regression: No
- _Time [hr]: 0.1
- _Test environment: HIL (manual)

## STC-BDY02-1559: E2E Protection for input signals 2
Signals Check
- _Object type: Misuse Test
- _Status: REVIEWED
- _Procedure: The ExteriorLightingSafetyZc1 shall receive the following signals:
  NMasterLightSwitchStatusFuSa
  BMasterLightSwitchFaultStatusFuSa
  EflcSafetyStatusMask
  NIgnitionStatus
- _Pass criteria: Verify that the message containing the signals is protected with an E2E protection mechanism.
- _Regression: No
- _Time [hr]: 0.1
- _Test environment: HIL (manual)

## STC-BDY02-1420: Brake Light Requested (1)
The ExteriorLightingSafetyZc1 detect if a communication error occurs in the transmission of the signals specified in [1686], [1688] within DTI = 200ms.
- _Object type: Misuse Test
- _Status: REVIEWED
- _Procedure: Communication Error on any of the below signals :
  NBrakePedalStatus
  pBrake
  gLongitudinal
  NgLongitudinal_Q
- _Pass criteria: Verify the Brake Light Requested
  within 200 ms
- _Regression: No
- _Time [hr]: 0.1
- _Test environment: HIL (manual)

## STC-BDY02-1560: Safe State #BDY02_RL_1 (1)
Upon detection of [1696] the ExteriorLightingSafetyZc1 transition to Safe State #BDY02_RL_1.
- _Object type: Misuse Test
- _Status: REVIEWED
- _Procedure: Communication Error on any of the below signals :
  NBrakePedalStatus
  pBrake
  gLongitudinal
  NgLongitudinal_Q
- _Pass criteria: Verify the Brake Light Requested
- _Regression: No
- _Time [hr]: 0.1
- _Test environment: HIL (manual)

## STC-BDY02-1561: Tail light activation 1
The ExteriorLightingSafetyZc1 detect if a communication error occurs in the transmission of the signals specified in [1691] within DTI = 200ms.
- _Object type: Misuse Test
- _Status: REVIEWED
- _Procedure: Communication Error on any of the below signals :
  NMasterLightSwitchStatusFuSa
  BMasterLightSwitchFaultStatusFuSa
- _Pass criteria: Verify the tail light activation
  within 200ms
- _Regression: No
- _Time [hr]: 0.1
- _Test environment: HIL (manual)

## STC-BDY02-1562: Safe State #BDY02_RL_2 (1)
Upon detection of [1733] the ExteriorLightingSafetyZc1 transition to Safe State #BDY02_RL_2.
- _Object type: Misuse Test
- _Status: REVIEWED
- _Procedure: Communication Error on any of the below signals :
  NMasterLightSwitchStatusFuSa
  BMasterLightSwitchFaultStatusFuSa
- _Pass criteria: Verify the tail light activation
- _Regression: No
- _Time [hr]: 0.1
- _Test environment: HIL (manual)

## STC-BDY02-1563: Tail light activation 2
The ExteriorLightingSafetyZc1 detect if a communication error occurs in the transmission of the signals specified in [1817] AND
(( NMasterLightSwitchStatusFuSa != 0x0 (OFF) OR (BMasterLightSwitchFaultStatusFuSa = 0x1 (TRUE STATE meaning ACTIVE FAULT)) AND BrakeLightConditionHappen is set false) within DTI = 200ms.
- _Object type: Misuse Test
- _Status: REVIEWED
- _Procedure: Communication Error on any of the below signals :
  NignitionStatus
  No Tail Light Request
  Brakelightcondition is false
- _Pass criteria: Verify the tail light activation
- _Regression: No
- _Time [hr]: 0.1
- _Test environment: HIL (manual)

## STC-BDY02-1564: Safe State #BDY02_RL_2 (2)
Upon detection of [STC-BDY02-1563] the ExteriorLightingSafetyZc1 shall transition to Safe State #BDY02_RL_2.
- _Object type: Misuse Test
- _Status: REVIEWED
- _Procedure: Communication Error on any of the below signals :
  NignitionStatus
  No Tail Light Request
  Brakelightcondition is false
- _Pass criteria: Verify the tail light activation
- _Regression: No
- _Time [hr]: 0.1
- _Test environment: HIL (manual)

## STC-BDY02-1565: Brake Light Requested (2)
The ExteriorLightingSafetyZc1 detect if a communication error occurs in the transmission of the signals specified in [1817] AND BrakeLightConditionHappen is set TRUE within DTI = 200ms.
- _Object type: Misuse Test
- _Status: REVIEWED
- _Procedure: Communication Error on any of the below signals :
  NignitionStatus
  No Tail Light Request
  Brakelightcondition is true
- _Pass criteria: Verify the Brake Light Requested
  within 200ms
- _Regression: No
- _Time [hr]: 0.1
- _Test environment: HIL (manual)

## STC-BDY02-1566: Safe State #BDY02_RL_1 (2)
Upon detection of [STC-BDY02-1565] the ExteriorLightingSafetyZc1 transition to Safe State #BDY02_RL_1.
- _Object type: Misuse Test
- _Status: REVIEWED
- _Procedure: Communication Error on any of the below signals :
  NignitionStatus
  No Tail Light Request
  Brakelightcondition is true
- _Pass criteria: Verify the Brake Light Requested
- _Regression: No
- _Time [hr]: 0.1
- _Test environment: HIL (manual)

## STC-BDY02-1567: Brake Light Requested (3)
The ExteriorLightingSafetyZc1 detect within DTI = 200ms if:
(pBrake_Q != valid && NBrakepedalStatus_Q != valid ) || gLongitudinal_Q != valid
- _Object type: Misuse Test
- _Status: REVIEWED
- _Procedure: Test Step :
  (pBrake_Q != valid && NBrakepedalStatus_Q != valid ) || gLogitudinal_Q != valid
- _Pass criteria: Verify the Brake Light Requested
- _Regression: No
- _Time [hr]: 0.1
- _Test environment: HIL (manual)

## STC-BDY02-1568: Safe State #BDY02_RL_1 (3)
Upon detection of [STC-BDY02-1567] the ExteriorLightingSafetyZc1 shall transition to Safe State #BDY02_RL_1.
- _Object type: Misuse Test
- _Status: REVIEWED
- _Procedure: Test Step :
  (pBrake_Q != valid && NBrakepedalStatus_Q != valid ) || gLogitudinal_Q != valid
- _Pass criteria: Verify the Brake Light Requested
- _Regression: No
- _Time [hr]: 0.1
- _Test environment: HIL (manual)

## STC-BDY02-1569: Command Sent Signals
Signals Check
- _Object type: Misuse Test
- _Status: REVIEWED
- _Procedure: The ExteriorLightingSafetyZc1 command the following signals:
  Stop_Tail_Outboard_PWR_RH (HSD3)
  Stop_Tail_Inboard_PWR_RH (HSD4)
  Stop_Tail_Outboard_PWR_LH (HSD8
  Stop_Tail_Inboard_PWR_LH (HSD7)
- _Pass criteria: Verify that the command signals are sent.
- _Regression: No
- _Time [hr]: 0.1
- _Test environment: HIL (manual)

## STC-BDY02-1570: E2E Protection for output signals
Signals Check
- _Object type: Misuse Test
- _Status: REVIEWED
- _Procedure: The ExteriorLightingSafetyZc1 shall command the following signal to ADI
  NRlcSafetyClusterMessage
  RlcSafetyStatusMask
- _Pass criteria: Verify that the message containing the signals is protected with an E2E protection mechanism.
- _Regression: No
- _Time [hr]: 0.1
- _Test environment: HIL (manual)

## STC-BDY02-1571: Brake Light/Tail Light warning sent to driver
The ExteriorLightingSafetyZc1 detect HW failures (i.e. short to ground, open, short to battery, out of range) on the signal specified in [1705] within DTI = 200ms.
- _Object type: Misuse Test
- _Status: REVIEWED
- _Procedure: HW Fault on :
  Stop_Tail_Outboard_PWR_RH (HSD3)
  Stop_Tail_Inboard_PWR_RH (HSD4)
  Stop_Tail_Outboard_PWR_LH (HSD8)
  Stop_Tail_Inboard_PWR_LH (HSD7)
- _Pass criteria: Verify that the Warning sent to driver (Brake Light/Tail Light warning)
  within 200ms
- _Regression: No
- _Time [hr]: 0.1
- _Test environment: HIL (manual)

## STC-BDY02-1572: Safe State #BDY02_RL_3
Upon detection of [STC-BDY02-1571], the ExteriorLightingSafetyZc1 transition to Safe State #BDY02_RL_3.
- _Object type: Misuse Test
- _Status: REVIEWED
- _Procedure: HW Fault on :
  Stop_Tail_Outboard_PWR_RH (HSD3)
  Stop_Tail_Inboard_PWR_RH (HSD4)
  Stop_Tail_Outboard_PWR_LH (HSD8)
  Stop_Tail_Inboard_PWR_LH (HSD7)
- _Pass criteria: Verify that the Warning sent to driver (Brake Light/Tail Light warning)
- _Regression: No
- _Time [hr]: 0.1
- _Test environment: HIL (manual)

## STC-BDY02-446

## R678
- _Object type: Cross Functional Test

## R679
- _Status: REVIEWED

## R680: Main beam telltale ON (ID:STC-HMI01-214)

## R681
Main beam ISO symbol shall be displayed to the driver when main beam latched function is active

## R682
- _Procedure: 1.Set ignition state=5
  2.Set Master Light Switch Position = 2
  3.Active main beam latched function by pushing the DIMS stalk forwards to a latched position

## R683
- _Pass criteria: NFlashMainSwitch = (0x2),Main_Beam_Latched_ Available.
  Main beam ISO symbol shall be displayed on the driver display

## R684
- _Regression: Yes

## R685
- _Time [hr]: 0.2

## R686
- _Test environment: Lab-Car (manual)

## STC-BDY02-447

## R688
- _Object type: Cross Functional Test

## R689
- _Status: REVIEWED

## R690: Main beam telltale OFF (ID:STC-HMI01-215)

## R691
Main beam ISO symbol shall be OFF on the driver when main beam latched function is NOT active

## R692
- _Procedure: 1.Set ignition state<5
  2.Set Master Light Switch Position = 2
  3.Active main beam latched function by pushing the DIMS stalk forwards to a latched position

## R693
- _Pass criteria: NFlashMainSwitch = (0x0),Main_Beam_Latched_ Unavailable.
  Main beam ISO symbol shall be OFF on the driver display

## R694
- _Regression: Yes

## R695
- _Time [hr]: 0.2

## R696
- _Test environment: Lab-Car (manual)

## STC-BDY02-448

## R698
- _Object type: Negative Test

## R699
- _Status: REVIEWED

## R700: Main beam telltale OFF

## R701
Main beam ISO symbol shall be OFF on the driver when main beam latched function is NOT active

## R702
- _Procedure: 1.Set ignition state=5
  2.Set Master Light Switch Position = 0||1
  3.Active main beam latched function by pushing the DIMS stalk forwards to a latched position

## R703
- _Pass criteria: NFlashMainSwitch = (0x0),Main_Beam_Latched_ Unavailable.
  Main beam ISO symbol shall be OFF on the driver display

## R704
- _Regression: Yes

## R705
- _Time [hr]: 0.2

## R706
- _Test environment: Lab-Car (manual)

## STC-BDY02-449

## R708
- _Object type: Nominal Test

## R709
- _Status: REVIEWED

## R710: Main beam telltale ON

## R711
Main beam ISO symbol shall be graphically displayed to the driver when main beam flash function is active

## R712
- _Procedure: 1.Set ignition state >= 2
  2.Active main beam flash function by pulling the DIMS stalk towards the steering wheel to a momentary position

## R713
- _Pass criteria: NFlashMainSwitch = (0x1),Main_Beam_Flash_ Available.
  Main beam ISO symbol shall be displayed on the driver display

## R714
- _Regression: Yes

## R715
- _Time [hr]: 0.2

## R716
- _Test environment: Lab-Car (manual)

## STC-BDY02-450

## R718
- _Object type: Negative Test

## R719
- _Status: REVIEWED

## R720: Main beam telltale OFF

## R721
Main beam ISO symbol shall be graphically displayed to the driver when main beam flash function is NOT active

## R722
- _Procedure: 1.Set ignition state < 2
  2.Active main beam flash function by pulling the DIMS stalk towards the steering wheel to a momentary position

## R723
- _Pass criteria: 2.NFlashMainSwitch = (0x0),Main_Beam_Flash_ Inactive.
  Main beam ISO symbol shall be OFF on the driver display

## R724
- _Regression: Yes

## R725
- _Time [hr]: 0.2

## R726
- _Test environment: Lab-Car (manual)

## STC-BDY02-453

## R728
- _Object type: Nominal Test

## R729
- _Status: REVIEWED

## R730: Main beam latched function available

## R731
Main beam latched function with master light position

## R732
- _Procedure: 1.Set ignition state >= 5
  2.Set Master Light Switch Position = 2

## R733
- _Pass criteria: Main_Beam_Latched_ Available but not activated,
  NFlashMainSwitch = (0x0)

## R734
- _Regression: Yes

## R735
- _Time [hr]: 0.2

## R736
- _Test environment: Lab-Car (auto)

## STC-BDY02-455

## R738
- _Object type: Negative Test

## R739
- _Status: REVIEWED

## R740: Main beam latched function NOT available with igniton state

## R741
Main beam latched function NOT available when ignition state<5

## R742
- _Procedure: 1.Set ignition state <5
  2.Set Master Light Switch Position = 2
  3.Push the DIMS stalk forwards to a latched position

## R743
- _Pass criteria: Main beam latched function not available

## R744
- _Regression: Yes

## R745
- _Time [hr]: 0.2

## R746
- _Test environment: Lab-Car (auto)

## STC-BDY02-572

## R748
- _Object type: Cross Functional Test

## R749
- _Status: REVIEWED

## R750: Main beam latched function NOT available with igniton state (ID:STC-ADA-02-08-530)

## R751
Main beam latched function NOT available when ignition state<5

## R752
- _Procedure: 1.Set ignition state <5
  2.Set Master Light Switch Position = Auto
  3.Push the DIMS stalk forwards to a latched position

## R753
- _Pass criteria: Main beam latched function not available

## R754
- _Regression: Yes

## R755
- _Time [hr]: 0.2

## R756
- _Test environment: Lab-Car (auto)

## STC-BDY02-457

## R758
- _Object type: Nominal Test

## R759
- _Status: REVIEWED

## R760: Main beam latched function deactivation with DIMS stalk

## R761
Deactivate main beam latched by pulling the DIMS stalk back from the latched position position

## R762
- _Procedure:
  1. Set NIgnitionStatus >= 5
  2. Main Beam Latched Function Available && NFlashMainSwitch = (0x2)
  2.Pull the DIMS stalk back from the latched position

## R763
- _Pass criteria: 2.NFlashMainSwitch != (0x2),Main_Beam_Latched_ Inactive && NMainBeamStatus = Active

## R764
- _Regression: No

## R765
- _Time [hr]: 0.2

## R766
- _Test environment: Lab-Car (auto)

## STC-BDY02-458

## R768
- _Object type: Nominal Test

## R769
- _Status: REVIEWED

## R770: Main beam latched function deactivation with ignition state

## R771
Deactivate main beam latched function with ignition state<5

## R772
- _Procedure: 1.Activate main beam latched function i.e., NIgnitionStatus >= 5 && NFlashMainSwitch = (0x2)
  2.Set ignition state < 5

## R773
- _Pass criteria: 2.NMainBeamStatus = = Inactive

## R774
- _Regression: Yes

## R775
- _Time [hr]: 0.2

## R776
- _Test environment: Lab-Car (auto)

## STC-BDY02-1064

## R778
- _Object type: Nominal Test

## R779
- _Status: REVIEWED

## R780: Main beam latched function deactivation with High severity

## R781
To cofirm ZB1 shall deactivate main beam latched when High severity crash occurs

## R782
- _Procedure: 1.Activate main beam latched function i.e., NIgnitionStatus >= 5 && NFlashMainSwitch = (0x2)2.Simulate NCrashSeverity = High from ORC on Chassis CAN

## R783
- _Pass criteria: NMainBeamStatus = Inactive

## R784
- _Regression: No

## R785
- _Time [hr]: 0.2

## R786
- _Test environment: Lab-Car (auto)

## STC-BDY02-1065

## R788
- _Object type: Nominal Test

## R789
- _Status: REVIEWED

## R790: Main beam latched function deactivation with low severity

## R791
To cofirm ZB1 shall deactivate main beam latched when Low severity crash occurs

## R792
- _Procedure: 1.Activate main beam latched function i.e., NIgnitionStatus >= 5 && NFlashMainSwitch = (0x2)2.Simulate NCrashSeverity = Low from ORC on Chassis CAN

## R793
- _Pass criteria: NMainBeamStatus = Inactive

## R794
- _Regression: No

## R795
- _Time [hr]: 0.2

## R796
- _Test environment: Lab-Car (auto)

## STC-BDY02-459

## R798
- _Object type: Nominal Test

## R799
- _Status: REVIEWED

## R800: Main beam latched function deactivation with master light

## R801
main beam latched function deactivation with master light switch position

## R802
- _Procedure: 1.Activate main beam latched function i.e., NIgnitionStatus >= 5 && NFlashMainSwitch = (0x2)
  2.Set Master Light Switch Position = 0||1

## R803
- _Pass criteria: 2.NFlashMainSwitch = 0x0,Main_Beam_Latched_ Unavailable

## R804
- _Regression: No

## R805
- _Time [hr]: 0.2

## R806
- _Test environment: Lab-Car (auto)

## STC-BDY02-462

## R808
- _Object type: Nominal Test

## R809
- _Status: REVIEWED

## R810: Main beam flash function activation

## R811
Main beam flash function activation with DIMS stalk

## R812
- _Procedure: 1.Set ignition state = 2
  2.Pull the DIMS stalk towards the steering wheel to a momentary position
  3.Repeast step 2 for all ignition states 3,4,5 and 6

## R813
- _Pass criteria: Main_Beam_Flash_ Active.
  NFlashMainSwitch = (0x1)

## R814
- _Regression: No

## R815
- _Time [hr]: 0.2

## R816
- _Test environment: Lab-Car (auto)

## STC-BDY02-474

## R818
- _Object type: Nominal Test

## R819
- _Status: REVIEWED

## R820: Main beam latched activation

## R821
Main beam fucntion activation

## R822
- _Procedure: 1.Set ignition state>=5
  2.Enable main beam latched function by
  pushing the DIMS stalk forwards to a latched position

## R823
- _Pass criteria: Main beam latched activated

## R824
- _Regression: No

## R825
- _Time [hr]: 0.1

## R826
- _Test environment: Lab-Car (auto)

## STC-BDY02-574

## R828
- _Object type: Nominal Test

## R829
- _Status: REVIEWED

## R830: Main beam flash function inactivation with release of DIMS stalk

## R831
Main beam flash function deactivation when ignition state<2

## R832
- _Procedure: 1.Activate main beam flash function
  2.Release DIMS stalk while main flash function is in activation

## R833
- _Pass criteria: 2. NMainBeamStatus = Inactive
  NFlashMainSwitch != Flash

## R834
- _Regression: No

## R835
- _Time [hr]: 0.2

## R836
- _Test environment: Lab-Car (auto)

## STC-BDY02-1626

## R838
- _Object type: Nominal Test

## R839
- _Status: REVIEWED

## R840: Main Beam Flash Function Deactivation

## R841
The main beam flash function shall be deactivated in the event of an ignition state transition to any state less than Ignition (5) or the state Connected Awake (7).

## R842
- _Procedure:
  1. NIgnitionStatus = 5
  2. NMainBeamStatus = Active
  3. NIgnitionStatus < Ignition
  ||
  NIgnitionStatus == Connected Awake

## R843
- _Pass criteria: 3. NMainBeamStatus = Inactive

## STC-BDY02-1442

## R845
- _Object type: Nominal Test

## R846
- _Status: REVIEWED

## R847: High Beam Short circuit fault

## R848
To confirm High Beam diagnostic strategy when short circuit fault occurs

## R849
- _Procedure: 1.Creat High Beam circuit fault i.e., short circuit fault
  2.After fault, make sure the drive feedback curent is out of normal operation thresholds

## R850
- _Pass criteria: NHighBeamActiveStatus = Fault && NMainBeamClusterMessage = Fault display on ICU

## R851
- _Regression: No

## R852
- _Time [hr]: 0.1

## R853
- _Test environment: Lab-Car (manual)

## STC-BDY02-1446

## R855
- _Object type: Cross Functional Test

## R856
- _Status: REVIEWED

## R857: High Beam Activation (ID:STC-ADA02-08-522)

## R858
To confirm High Beam activation

## R859
- _Procedure: 1.Set Iginition State >=5
  2.Activate Main beam flash latched function or main beam flash function

## R860
- _Pass criteria: NHighBeamActiveStatus = Active

## R861
- _Regression: No

## R862
- _Time [hr]: 0.1

## R863
- _Test environment: Lab-Car (auto)

## STC-BDY02-1443

## R865
- _Object type: Nominal Test

## R866
- _Status: REVIEWED

## R867: High Beam open circuit fault

## R868
To confirm High Beam diagnostic strategy when open circuit fault occurs

## R869
- _Procedure: 1.Creat DTRL circuit fault i.e., open circuit fault
  2.After fault, make sure the drive feedback curent is out of normal operation thresholds

## R870
- _Pass criteria: NHighBeamActiveStatus = Fault && NMainBeamClusterMessage = Fault display on ICU

## R871
- _Regression: No

## R872
- _Time [hr]: 0.1

## R873
- _Test environment: Lab-Car (manual)

## STC-BDY02-1444

## R875
- _Object type: Nominal Test

## R876
- _Status: REVIEWED

## R877: High Beam circuit circuit fault reset

## R878
To confirm High Beam lights fault reset with new ignition cycle

## R879
- _Procedure: 1.Creat DTRL circuit fault i.e., Open circuit fault
  2.After fault, make sure the drive feedback curent is out of normal operation thresholds
  3.Start new ignition cycle

## R880
- _Pass criteria: NHighBeamActiveStatus = Inactive && NMainBeamClusterMessage = Fault display shall e cleared on ICU

## R881
- _Regression: No

## R882
- _Time [hr]: 0.1

## R883
- _Test environment: Lab-Car (manual)

## STC-BDY02-593

## R885
- _Object type: Nominal Test

## R886
- _Status: REVIEWED

## R887: MasterLightSwitchResistorLadder1 voltage

## R888
To confirm MasterLightSwitchResistorLadder1 voltage to detect MLS position

## R889
- _Procedure: 1.Change MasterLightSwitchResistorLadder1 voltage to STEP1 i.e., Nominal voltage(1.46),Min vol(1.43),Max(1.49)
  2.Change MasterLightSwitchResistorLadder1 voltage to STEP2 i.e., Nominal voltage(2.12),Min vol(2.08),Max(2.16)
  3.Change MasterLightSwitchResistorLadder1 voltage to STEP3 i.e., Nominal voltage(2.83),Min vol(2.78),Max(2.89)
  4.Change MasterLightSwitchResistorLadder1 voltage to STEP4 i.e., Nominal voltage(3.58),Min vol(3.51),Max(3.65)
  5.Change MasterLightSwitchResistorLadder1 voltage to previous state i.e.,Nominal voltage (4.26),Min vol(4.17),Max(4.35)
  6.Change MasterLightSwitchResistorLadder1 voltage to
  FAULT_MLS(Open circuit/Short to batt) i.e., Nominal voltage(5),Min vol(4.75),Max(5)
  7.Change MasterLightSwitchResistorLadder1 voltage to FAULT_MLS(Short to gnd) i.e., Nominal voltage(0),Min vol(0),Max(0.75)
  8.Change MasterLightSwitchResistorLadder1 voltage to FAULT_MLS(Out of range) i.e.,
  > 0.75 and < 1.43,
  > 1.49 and < 2.08,
  > 2.16 and < 2.78,
  > 2.89 and < 3.51,
  > 3.65 and < 4.17,
  > 4.35 and < 4.75

## R890
- _Pass criteria: 1.MLS position is set to Off_NMastrLghtSwtchPos
  2.MLS position is set to Auto_NMastrLghtSwtchPos
  3.MLS position is set to Side_Lamps_NMastrLghtSwtchPos
  4.MLS position is set to Dipped_Beam_NMastrLghtSwtchPos
  5.MLS position is set to Previous State
  6.MLS position is set to Auto_NMastrLghtSwtchPos
  7.MLS position is set to Auto_NMastrLghtSwtchPos
  8.MLS position is set to Auto_NMastrLghtSwtchPos

## R891
- _Regression: No

## R892
- _Time [hr]: 0.2

## R893
- _Test environment: Lab-Car (auto)

## STC-BDY02-594

## R895
- _Object type: Nominal Test

## R896
- _Status: REVIEWED

## R897: MasterLightSwitchResistorLadder2 voltage

## R898
To confirm MasterLightSwitchResistorLadder2 voltage to detect MLS Fog request

## R899
- _Procedure: 1.Change MasterLightSwitchResistorLadder2 voltage to STEP1 i.e., Nominal voltage(3.85),Min vol(3.77),Max(3.93)
  2.Change MasterLightSwitchResistorLadder2 voltage to STEP2 i.e., Nominal voltage(TBD),Min vol(TBD),Max(TBD)
  3.Change MasterLightSwitchResistorLadder2 voltage to STEP3 i.e., Nominal voltage(2.04),Min vol(2),Max(2.08)
  4.Change MasterLightSwitchResistorLadder2 voltage to
  FAULT_MLS(Open circuit/Short to batt) i.e., Nominal voltage(5),Min vol(4.75),Max(5)
  5.Change MasterLightSwitchResistorLadder2 voltage to FAULT_MLS(Short to gnd) i.e., Nominal voltage(0),Min vol(0),Max(0.75)
  6.Change MasterLightSwitchResistorLadder2 voltage to FAULT_MLS(Out of range) i.e.,
  > 0.75 and < 2.0
  > 2.08 and < 3.77
  > 3.93 and < 4.75

## R900
- _Pass criteria: 1.MLS fog reuest is set to OFF_BOffOnState(No press)
  2.MLS fog reuest is set to OFF_BOffOnState(Front fog)
  3.MLS fog reuest is set to ON_BOffOnState(Rear fog)
  4.MLS fog reuest is set to OFF_BOffOnState
  5.MLS fog reuest is set to OFF_BOffOnState
  6.MLS fog reuest is set to OFF_BOffOnState

## R901
- _Regression: No

## R902
- _Time [hr]: 0.25

## R903
- _Test environment: Lab-Car (auto)

## STC-BDY02-595

## R905
- _Object type: Nominal Test

## R906
- _Status: REVIEWED

## R907: MLS fault display

## R908
To confirm the user display when MLS is faulty

## R909
- _Procedure: 1.Set MLS to faulty state,
  Set MasterLightSwitchResistorLadder1 /MasterLightSwitchResistorLadder2 voltage to
  FAULT_MLS(Open circuit/Short to batt) i.e., Nominal voltage(5),Min vol(4.75),Max(5)

## R910
- _Pass criteria: ZB1 shall set 0x01 TBC DTC along with the fault display on DD

## R911
- _Regression: No

## R912
- _Time [hr]: 0.5

## R913
- _Test environment: Lab-Car (auto)

## STC-BDY02-1435

## R915
- _Object type: Nominal Test

## R916
- _Status: REVIEWED

## R917: MasterLightSwitchResistorLadder1 voltage

## R918
To confirm MasterLightSwitchResistorLadder1 voltage to detect MLS position

## R919
- _Procedure: 1.Change MasterLightSwitchResistorLadder1 voltage to STEP1 i.e., Nominal voltage(1.46),Min vol(1.43),Max(1.49)
  2.Change MasterLightSwitchResistorLadder1 voltage to STEP2 i.e., Nominal voltage(2.12),Min vol(2.08),Max(2.16)
  3.Change MasterLightSwitchResistorLadder1 voltage to STEP3 i.e., Nominal voltage(2.83),Min vol(2.78),Max(2.89)
  4.Change MasterLightSwitchResistorLadder1 voltage to STEP4 i.e., Nominal voltage(3.58),Min vol(3.51),Max(3.65)
  5.Change MasterLightSwitchResistorLadder1 voltage to previous state i.e.,Nominal voltage (4.26),Min vol(4.17),Max(4.35)
  6.Change MasterLightSwitchResistorLadder1 voltage to
  FAULT_MLS(Open circuit/Short to batt) i.e., Nominal voltage(5),Min vol(4.75),Max(5)
  7.Change MasterLightSwitchResistorLadder1 voltage to FAULT_MLS(Short to gnd) i.e., Nominal voltage(0),Min vol(0),Max(0.75)
  8.Change MasterLightSwitchResistorLadder1 voltage to FAULT_MLS(Out of range) i.e.,
  > 0.75 and < 1.43,
  > 1.49 and < 2.08,
  > 2.16 and < 2.78,
  > 2.89 and < 3.51,
  > 3.65 and < 4.17,
  > 4.35 and < 4.75

## R920
- _Pass criteria: 1.MLS position is set to Off_NMastrLghtSwtchPos
  2.MLS position is set to Auto_NMastrLghtSwtchPos
  3.MLS position is set to Side_Lamps_NMastrLghtSwtchPos
  4.MLS position is set to Dipped_Beam_NMastrLghtSwtchPos
  5.MLS position is set to Previous State
  6.MLS position is set to Auto_NMastrLghtSwtchPos
  7.MLS position is set to Auto_NMastrLghtSwtchPos
  8.MLS position is set to Auto_NMastrLghtSwtchPos

## R921
- _Regression: No

## R922
- _Time [hr]: 0.2

## R923
- _Test environment: Lab-Car (auto)

## STC-BDY02-1436

## R925
- _Object type: Nominal Test

## R926
- _Status: REVIEWED

## R927: MasterLightSwitchResistorLadder2 voltage

## R928
To confirm MasterLightSwitchResistorLadder2 voltage to detect MLS Fog request

## R929
- _Procedure: 1.Change MasterLightSwitchResistorLadder2 voltage to STEP1 i.e., Nominal voltage(3.85),Min vol(3.77),Max(3.93)
  2.Change MasterLightSwitchResistorLadder2 voltage to STEP2 i.e., Nominal voltage(TBD),Min vol(TBD),Max(TBD)
  3.Change MasterLightSwitchResistorLadder2 voltage to STEP3 i.e., Nominal voltage(2.04),Min vol(2),Max(2.08)
  4.Change MasterLightSwitchResistorLadder2 voltage to
  FAULT_MLS(Open circuit/Short to batt) i.e., Nominal voltage(5),Min vol(4.75),Max(5)
  5.Change MasterLightSwitchResistorLadder2 voltage to FAULT_MLS(Short to gnd) i.e., Nominal voltage(0),Min vol(0),Max(0.75)
  6.Change MasterLightSwitchResistorLadder2 voltage to FAULT_MLS(Out of range) i.e.,
  > 0.75 and < 2.0
  > 2.08 and < 3.77
  > 3.93 and < 4.75

## R930
- _Pass criteria: 1.MLS fog reuest is set to OFF_BOffOnState(No press)
  2.MLS fog reuest is set to OFF_BOffOnState(Front fog)
  3.MLS fog reuest is set to ON_BOffOnState(Rear fog)
  4.MLS fog reuest is set to OFF_BOffOnState
  5.MLS fog reuest is set to OFF_BOffOnState
  6.MLS fog reuest is set to OFF_BOffOnState

## R931
- _Regression: No

## R932
- _Time [hr]: 0.25

## R933
- _Test environment: Lab-Car (auto)

## STC-BDY02-1437

## R935
- _Object type: Nominal Test

## R936
- _Status: REVIEWED

## R937: MLS fault display

## R938
To confirm the user display when MLS is faulty

## R939
- _Procedure: 1.Set MLS to faulty state,
  Set MasterLightSwitchResistorLadder1 /MasterLightSwitchResistorLadder2 voltage to
  FAULT_MLS(Open circuit/Short to batt) i.e., Nominal voltage(5),Min vol(4.75),Max(5)

## R940
- _Pass criteria: ZB1 shall set 0x01 TBC DTC along with the fault display on DD

## R941
- _Regression: No

## R942
- _Time [hr]: 0.5

## R943
- _Test environment: Lab-Car (auto)

## STC-BDY02-1088

## R945
- _Object type: Cross Functional Test

## R946
- _Status: REVIEWED

## R947: NMasterLightStatus = Dipped beam latched (ID:STC-BDY03-51, STC-HMI01-209)

## R948
To confirm master light status as Dipped beam latched when dipped beam is activated

## R949
- _Procedure: 1.Set ignition state =5
  2.Activate dipped beam function(i.e.,Position master light switch in 0x2)
  3.Check for NMasterLightStatus Ethernet signal

## R950
- _Pass criteria: NMasterLightStatus = 0x2(Dipped_Beam_NMasterLightStatus)

## R951
- _Regression: No

## R952
- _Time [hr]: 0.3

## R953
- _Test environment: Lab-Car (auto)

## STC-BDY02-1087

## R955
- _Object type: Cross Functional Test

## R956
- _Status: REVIEWED

## R957: NMasterLightStatus = Side Lights (ID:STC-HMI01-226)

## R958
To confirm master light status as side lights when side light function is activated

## R959
- _Procedure: 1.Set ignition state =5
  2.Activate side lights function(i.e.,Position master light switch in 0x1)
  3.Check for NMasterLightStatus Ethernet signal

## R960
- _Pass criteria: NMasterLightStatus = 0x1(Side_Lamps_NMasterLightStatus)

## R961
- _Regression: No

## R962
- _Time [hr]: 0.3

## R963
- _Test environment: Lab-Car (auto)

## STC-BDY02-1247

## R965
- _Object type: Cross Functional Test

## R966
- _Status: REVIEWED

## R967: NMasterLightStatus = OFF Lights (ID:STC-ADA02-08-527)

## R968
To confirm master light status as OFF light when side light and the Dipped beam are inactive

## R969
- _Procedure: 1.Set ignition state =5
  2. Set NSideLightLeftStatus == inactive && NSideLightRightStatus == inactive && NDippedBeamLeftStatus == inactive && NDippedBeamRightStatus == inactive
  3.Check for NMasterLightStatus Ethernet signal

## R970
- _Pass criteria: NMasterLightStatus = 0x0 (Off_NMasterLightStatus)

## R971
- _Regression: No

## R972
- _Time [hr]: 0.3

## R973
- _Test environment: Lab-Car (auto)

## STC-BDY02-1096

## R975
- _Object type: Nominal Test

## R976
- _Status: REVIEWED

## R977: Dipped beam latch function inactivation with ignition state

## R978
To confirm dipped beam latched function inactivation when ignition state <5

## R979
- _Procedure: 1.Activate dipped beam latched function( i.e.,Set NIgnitionStatus == Ignition || Powertrain Activation && Position NMasterLightSwitchPosition = 0x2(Dipped Beam))
  2.Set NIgnitionStatus < 0x5

## R980
- _Pass criteria: Dipped Beam Latched Function inactivation.
  NDippedBeamLeftStatus,NDippedBeamRightStatus=Off &&
  NLHDippedBeamLampActiveSts,NRHDippedBeamLampActiveSts=inActive

## R981
- _Regression: No

## R982
- _Time [hr]: 0.3

## R983
- _Test environment: Lab-Car (auto)

## STC-BDY02-1097

## R985
- _Object type: Nominal Test

## R986
- _Status: REVIEWED

## R987: Dipped beam latch inactivation with ignition state

## R988
To confirm dipped beam latched function inactivation when ignition state = 0x7

## R989
- _Procedure: 1.Activate dipped beam latched function( i.e.,Set NIgnitionStatus == Ignition || Powertrain Activation && Position NMasterLightSwitchPosition = 0x2(Dipped Beam))
  2.Set NIgnitionStatus == Connected Awake 0x7

## R990
- _Pass criteria: Dipped Beam Latched Function inactivation.
  NDippedBeamLeftStatus,NDippedBeamRightStatus=Off &&
  NLHDippedBeamLampActiveSts,NRHDippedBeamLampActiveSts=inActive

## R991
- _Regression: No

## R992
- _Time [hr]: 0.3

## R993
- _Test environment: Lab-Car (auto)

## STC-BDY02-1098

## R995
- _Object type: Nominal Test

## R996
- _Status: REVIEWED

## R997: Dipped beam latch activation with High severity

## R998
To confirm dipped beam latched function activation with high severity

## R999
- _Procedure: 1.Set NIgnitionStatus == 0x2
  2.Set NCrashSeverity=High

## R1000
- _Pass criteria: Dipped Beam Latched Function Available.
  NDippedBeamLeftStatus,NDippedBeamRightStatus=On_NIlluminationActvStat &&
  NLHDippedBeamLampActiveSts,NRHDippedBeamLampActiveSts=Active_NActivatnSts

## R1001
- _Regression: No

## R1002
- _Time [hr]: 0.3

## R1003
- _Test environment: Lab-Car (auto)

## STC-BDY02-1445

## R1005
- _Object type: Nominal Test

## R1006
- _Status: REVIEWED

## R1007: Dipped beam deactivation

## R1008
Dipped beam fucntion deactivation when MLS = Side light position

## R1009
- _Procedure: 1.Activate Dipped beam
  Set ignition state>=5 && Master light switch position is at Dipped,Master Light Switch Position = 2
  2.Deactivate Dipped beam
  Set ignition state>=5 && Master light switch position is at Dipped,Master Light Switch Position = 1

## R1010
- _Pass criteria: NDippedBeamLeftStatus = Inactive
  NDippedBeamRightStatus = Inactive

## R1011
- _Regression: No

## R1012
- _Time [hr]: 0.1

## R1013
- _Test environment: Lab-Car (auto)

## STC-BDY02-1099

## R1015
- _Object type: Nominal Test

## R1016
- _Status: REVIEWED

## R1017: Dipped beam latch activation with Low severity

## R1018
To confirm dipped beam latched function activation with low severity

## R1019
- _Procedure: 1.Set NIgnitionStatus == 0x2
  2.Set NCrashSeverity=Low

## R1020
- _Pass criteria: Dipped Beam Latched Function Available.
  NDippedBeamLeftStatus,NDippedBeamRightStatus=On_NIlluminationActvStat &&
  NLHDippedBeamLampActiveSts,NRHDippedBeamLampActiveSts=Active_NActivatnSts

## R1021
- _Regression: No

## R1022
- _Time [hr]: 0.3

## R1023
- _Test environment: Lab-Car (auto)

## STC-BDY02-596

## R1025
- _Object type: Nominal Test

## R1026
- _Status: REVIEWED

## R1027: Dipped beam while crash

## R1028
dipped beam illumination when crash occurs

## R1029
- _Procedure: 1.Set iNgnition state=5
  2.Simulate NCrashSeverity == High Severity from ORC on Chassis CAN
  3.Simulate NCrashSeverity !== High Severity from ORC on Chassis CAN

## R1030
- _Pass criteria: 2.Dipped beam lamps shall be illuminated
  3.Dipped beam lamps illumination shall be deactivated

## R1031
- _Regression: Yes

## R1032
- _Time [hr]: 0.5

## R1033
- _Test environment: Lab-Car (auto)

## STC-BDY02-1092

## R1035
- _Object type: Nominal Test

## R1036
- _Status: REVIEWED

## R1037: ISO symbol when dipped beam is activated

## R1038
To confirm ISO symbol when dipped beam is activated

## R1039
- _Procedure: 1.Activate dipped beam latched function( i.e.,Set NIgnitionStatus == Ignition || Powertrain Activation && Position NMasterLightSwitchPosition = 0x2(Dipped Beam))
  2.Check ISO symbol

## R1040
- _Pass criteria: Driver Display dipped beam tell tale illuminated in DDP

## R1041
- _Regression: No

## R1042
- _Time [hr]: 0.3

## R1043
- _Test environment: Lab-Car (manual)

## STC-BDY02-1091

## R1045
- _Object type: Nominal Test

## R1046
- _Status: REVIEWED

## R1047: Dipped beam latch function activation

## R1048
To confirm dipped beam latched function activation with MLS=0x2

## R1049
- _Procedure: 1.Set NIgnitionStatus == Ignition || Powertrain Activation
  2.Position NMasterLightSwitchPosition = 0x2(Dipped Beam)

## R1050
- _Pass criteria: Dipped Beam Latched Function Available.
  NDippedBeamLeftStatus,NDippedBeamRightStatus=On_NIlluminationActvStat &&
  NLHDippedBeamLampActiveSts,NRHDippedBeamLampActiveSts=Active_NActivatnSts

## R1051
- _Regression: No

## R1052
- _Time [hr]: 0.3

## R1053
- _Test environment: Lab-Car (auto)

## STC-BDY02-1105

## R1055
- _Object type: Nominal Test

## R1056
- _Status: REVIEWED

## R1057: Rear lights activation with PWM

## R1058
To confirm rear lights activation when PWM duty cycle is 88%

## R1059
- _Procedure: 1.Set NIgnitionState = 0x5
  || PowerTrainStatus = Torque Available
  2.Set PWM duty cycle to 88% using XCp i.e., TailLampsPWM = 88%

## R1060
- _Pass criteria: NTailLampLeftStatus == Active
  NTailLampRightStatus == Active
  &&
  NLHTailLampActiveSts==Active_NActivatnSts
  NRHTailLampActiveSts==
  Active_NActivatnSts

## R1061
- _Regression: No

## R1062
- _Time [hr]: 0.2

## R1063
- _Test environment: Lab-Car (auto)

## STC-BDY02-1101

## R1065
- _Object type: Nominal Test

## R1066
- _Status: REVIEWED

## R1067: Rear lights activation

## R1068
To confirm rear lights activation when igniton>=2

## R1069
- _Procedure: NIgnitionStatus >= Awake (0x2) &&
  NIgnitionStatus != Connected Awake (0x7)
  2.Set Master Light Switch is in the side or dipped lights position

## R1070
- _Pass criteria: NTailLightLeftStatus = Active
  NTailLightRightStatus = Active

## R1071
- _Regression: No

## R1072
- _Time [hr]: 0.2

## R1073
- _Test environment: Lab-Car (auto)

## STC-BDY02-1107

## R1075
- _Object type: Nominal Test

## R1076
- _Status: REVIEWED

## R1077: Rear lamp Short circuit fault

## R1078
To confirm Rear lights diagnostic strategy when short circuit fault occurs

## R1079
- _Procedure: 1.Creat rear lights circuit fault i.e., short circuit fault
  2.After fault, make sure the drive feedback curent is out of normal operation thresholds

## R1080
- _Pass criteria: 1.NLHRearTailLampActiveSts = TailLampFault
  NRHRearTailLampActiveSts = TailLampFault
  2.A DTC shall be raised
  3.NTailLampClusterMessage = Fault shall be sent to ICU

## R1081
- _Regression: No

## R1082
- _Time [hr]: 0.1

## R1083
- _Test environment: Lab-Car (auto)

## STC-BDY02-1110

## R1085
- _Object type: Nominal Test

## R1086
- _Status: REVIEWED

## R1087: Rear lamp Open circuit fault

## R1088
To confirm Rear lights diagnostic strategy when Open circuit fault occurs

## R1089
- _Procedure: 1.Creat rear lights circuit fault i.e., Open circuit fault
  2.After fault, make sure the drive feedback curent is out of normal operation thresholds

## R1090
- _Pass criteria: 1.NLHRearTailLampActiveSts = TailLampFault
  NRHRearTailLampActiveSts = TailLampFault
  2.A DTC shall be raised
  3.NTailLampClusterMessage = Fault shall be sent to ICU

## R1091
- _Regression: No

## R1092
- _Time [hr]: 0.1

## R1093
- _Test environment: Lab-Car (auto)

## STC-BDY02-1109

## R1095
- _Object type: Nominal Test

## R1096
- _Status: REVIEWED

## R1097: Rear lamp circuit circuit fault reset

## R1098
To confirm Rear lights fault reset with new ignition cycle

## R1099
- _Procedure: 1.Creat rear lights circuit fault i.e., Open circuit fault
  2.After fault, make sure the drive feedback curent is out of normal operation thresholds
  3.Start new ignition cycle

## R1100
- _Pass criteria: NLHRearTailLampActiveSts = TailLampInactive
  NRHRearTailLampActiveSts = RearLampInactive

## R1101
- _Regression: No

## R1102
- _Time [hr]: 0.1

## R1103
- _Test environment: Lab-Car (auto)

## STC-BDY02-1112

## R1105
- _Object type: Nominal Test

## R1106
- _Status: REVIEWED

## R1107: Dipped beam activation with Automatic Light

## R1108
To confirm dipped beam active with automatic light

## R1109
- _Procedure: 1.Set NPowertrainStatus == Available
  2.Set
  NMasterLightSwitchPosition == Auto
  3.RLS shall request the dipped beam to be active i.e., NLightSwitchRequest == ON (0x01)

## R1110
- _Pass criteria: ZB1 shall enable dipped beam activation, BLH_DippedBeamActivate_Req = Active
  BRH_DippedBeamActivate_Req = Active

## R1111
- _Regression: No

## R1112
- _Time [hr]: 0.1

## R1113
- _Test environment: Lab-Car (auto)

## STC-BDY02-1116

## R1115
- _Object type: Nominal Test

## R1116
- _Status: REVIEWED

## R1117: Dipped beam deactivation with Automatic Light when MLS is in Side Light or Dipped Beam

## R1118
To confirm dipped beam deactive with automatic light when MLS is in Side Light or Dipped Beam

## R1119
- _Procedure: 1.Activate dipped beam function(Set NPowertrainStatus == Available &&
  NMasterLightSwitchPosition == Auto && NLightSwitchRequest == ON (0x01))
  2. Set MLS is in Side Light or Dipped Beam

## R1120
- _Pass criteria: ZB1 shall deactivate the dipped beam function , BLH_DippedBeamActivate_Req = Inactive
  BRH_DippedBeamActivate_Req = Inactive

## R1121
- _Regression: No

## R1122
- _Time [hr]: 0.1

## R1123
- _Test environment: Lab-Car (auto)

## STC-BDY02-1115

## R1125
- _Object type: Nominal Test

## R1126
- _Status: REVIEWED

## R1127: Dipped beam deactivation with Automatic Light when Powertrain status is unavailable

## R1128
To confirm dipped beam deactive with automatic light when Powertrain status is unavailable

## R1129
- _Procedure: 1.Activate dipped beam function(Set NPowertrainStatus == Available &&
  NMasterLightSwitchPosition == Auto && NLightSwitchRequest == ON (0x01))
  2. Set Powertrain status is unavailable, NPowertrainStatus !== Available

## R1130
- _Pass criteria: ZB1 shall deactivate the dipped beam function , BLH_DippedBeamActivate_Req = Inactive
  BRH_DippedBeamActivate_Req = Inactive

## R1131
- _Regression: No

## R1132
- _Time [hr]: 0.1

## R1133
- _Test environment: Lab-Car (auto)

## STC-BDY02-1117

## R1135
- _Object type: Nominal Test

## R1136
- _Status: REVIEWED

## R1137: Dipped beam deactivation with Automatic Light when Fog light is Active

## R1138
To confirm dipped beam deactive with automatic light when Fog light is Active

## R1139
- _Procedure: 1.Activate dipped beam function(Set NPowertrainStatus == Available &&
  NMasterLightSwitchPosition == Auto && NLightSwitchRequest == ON (0x01))
  2. Activaate Fog light , NFogLightRStatus == Active

## R1140
- _Pass criteria: ZB1 shall deactivate the dipped beam function , BLH_DippedBeamActivate_Req = Inactive
  BRH_DippedBeamActivate_Req = Inactive

## R1141
- _Regression: No

## R1142
- _Time [hr]: 0.1

## R1143
- _Test environment: Lab-Car (auto)

## STC-BDY02-1114

## R1145
- _Object type: Nominal Test

## R1146
- _Status: REVIEWED

## R1147: Dipped beam deactivation with Automatic Light

## R1148
To confirm dipped beam deactive with automatic light

## R1149
- _Procedure: 1.Activate dipped beam function(Set NPowertrainStatus == Available &&
  NMasterLightSwitchPosition == Auto && NLightSwitchRequest == ON (0x01))
  2.Light Switch Request is OFF, NLightSwitchRequest == OFF (0x00)

## R1150
- _Pass criteria: ZB1 shall deactivate the dipped beam function , BLH_DippedBeamActivate_Req = Inactive
  BRH_DippedBeamActivate_Req = Inactive

## R1151
- _Regression: No

## R1152
- _Time [hr]: 0.1

## R1153
- _Test environment: Lab-Car (auto)

## STC-BDY02-1121

## R1155
- _Object type: Nominal Test

## R1156
- _Status: REVIEWED

## R1157: Dipped beam activation with Automatic Light recovers only in next ign cycle

## R1158
To confirm dipped beam function shall only recover after an ignition cycle with all valid singals

## R1159
- _Procedure: 1.Activate dipped beam function(Set NPowertrainStatus == Available &&
  NMasterLightSwitchPosition == Auto && NLightSwitchRequest == ON (0x01))
  2.Light Switch Request is OFF, NLightSwitchRequest == OFF(0x0)
  3.Set NLightSwitchRequest == ON (0x01)
  4.Restart the new ignition cycle

## R1160
- _Pass criteria: ZB1 shall deactivate the dipped beam function , BLH_DippedBeamActivate_Req = Inactive
  BRH_DippedBeamActivate_Req = Inactive in the current ignition cycle.
  Dipped beam function shall recover only in the new ignition cycle

## R1161
- _Regression: No

## R1162
- _Time [hr]: 0.1

## R1163
- _Test environment: Lab-Car (auto)

## STC-BDY02-1447

## R1165
- _Object type: Nominal Test

## R1166
- _Status: REVIEWED

## R1167: RLS Diagnostics

## R1168
To confirm automatic light functuion when RLS is unavailable

## R1169
- _Procedure: 1.Set ignition state >=5
  2.Master Light Switch Position set as AUTO && NPowertrainStatus == Torque Available && (NIgnitionStatus == 0x5 || 0x6) && NFogLightStatus == Inactive && NLightSwitchRequest == Fault (0x02)

## R1170
- _Pass criteria: NDippedBeamLeftStatus = Active
  NDippedBeamRightStatus = Active

## R1171
- _Regression: No

## R1172
- _Time [hr]: 0.1

## R1173
- _Test environment: Lab-Car (auto)

## STC-BDY02-581

## R1175
- _Object type: Nominal Test

## R1176
- _Status: REVIEWED

## R1177: Off light function activation

## R1178
Off light function activation when IGN>=5

## R1179
- _Procedure: 1.Set ignition state =5
  2.Set Master light switch to OFF position from Auto for time period >=MLSOFFPeriod
  3.Set vehicle speed <=4kph
  4.Off light function activation period < LampsOFFTimer

## R1180
- _Pass criteria: OFF Light Function available.Dipped beam shall be deactivated

## R1181
- _Regression: Yes

## R1182
- _Time [hr]: 0.3

## R1183
- _Test environment: Lab-Car (auto)

## STC-BDY02-590

## R1185
- _Object type: Nominal Test

## R1186
- _Status: REVIEWED

## R1187: Off light function activation

## R1188
Off light function activation when IGN>=5

## R1189
- _Procedure: 1.Set ignition state =6(torque available)
  2.Set Master light switch to OFF position from Auto for time period >=MLSOFFPeriod
  3.Set vehicle speed <=4kph
  4.Off light function activation period < LampsOFFTimer
  5.Activate DTRL/Hazard/Main beam/DIMS function while Off light is being actve

## R1190
- _Pass criteria: OFF Light Function available.Dipped beam shall be deactivated.
  DTRL, Hazards, Main Beam Flash and DIMS functions shall be still available when the OFF Light function is being activated

## R1191
- _Regression: Yes

## R1192
- _Time [hr]: 0.3

## R1193
- _Test environment: Lab-Car (auto)

## STC-BDY02-585

## R1195
- _Object type: Nominal Test

## R1196
- _Status: REVIEWED

## R1197: Off light function unavailable

## R1198
Off light function unavailable when vehicle speed > 4kph

## R1199
- _Procedure: 1.Set ignition state >=5
  2.Set Master light switch to OFF position from Auto for time period >=MLSOFFPeriod
  3.Set vehicle speed > 4kph
  4.Off light function activation period < LampsOFFTimer

## R1200
- _Pass criteria: OFF Light Function Unavailable

## R1201
- _Regression: No

## R1202
- _Time [hr]: 0.3

## R1203
- _Test environment: Lab-Car (auto)

## STC-BDY02-586

## R1205
- _Object type: Nominal Test

## R1206
- _Status: REVIEWED

## R1207: Off light function unavailable

## R1208
Off light function unavailable with master light switch position is set to AUTO

## R1209
- _Procedure: 1.Set ignition state >=5
  2.Set Master light switch to OFF for time period >=MLSOFFPeriod
  3.Set vehicle speed <= 4kph
  4.Set MSL=Auto before Off light function activation period < LampsOFFTimer

## R1210
- _Pass criteria: OFF Light Function available for timeperiod LampsOFFTimer(30sec)

## R1211
- _Regression: No

## R1212
- _Time [hr]: 0.3

## R1213
- _Test environment: Lab-Car (auto)

## STC-BDY02-588

## R1215
- _Object type: Nominal Test

## R1216
- _Status: REVIEWED

## R1217: Off light function unavailable

## R1218
Off light function unavailable with master light switch position is set to side lights

## R1219
- _Procedure: 1.Set ignition state >=5
  2.Set Master light switch to OFF for time period >=MLSOFFPeriod
  3.Set vehicle speed <= 4kph
  4.Set MSL=side lights before Off light function activation period < LampsOFFTimer

## R1220
- _Pass criteria: OFF Light Function Unavailable

## R1221
- _Regression: No

## R1222
- _Time [hr]: 0.3

## R1223
- _Test environment: Lab-Car (auto)

## STC-BDY02-589

## R1225
- _Object type: Nominal Test

## R1226
- _Status: REVIEWED

## R1227: Off light function unavailable

## R1228
Off light function unavailable with master light switch position is set to dipped beam

## R1229
- _Procedure: 1.Set ignition state >=5
  2.Set Master light switch to OFF for time period >=MLSOFFPeriod
  3.Set vehicle speed <= 4kph
  4.Set MSL=dipped before Off light function activation period < LampsOFFTimer

## R1230
- _Pass criteria: OFF Light Function Unavailable

## R1231
- _Regression: No

## R1232
- _Time [hr]: 0.3

## R1233
- _Test environment: Lab-Car (auto)

## STC-BDY02-587

## R1235
- _Object type: Nominal Test

## R1236
- _Status: REVIEWED

## R1237: Off light function deactivation

## R1238
Off light function deactivation after LampsOFFTimer duration

## R1239
- _Procedure: 1.Set ignition state >=5
  2.Set Master light switch to OFF position from Auto for time period >=MLSOFFPeriod
  3.Set vehicle speed <= 4kph
  4.Off light function activation period > LampsOFFTimer

## R1240
- _Pass criteria: OFF Light Function deactivated for after 30sec

## R1241
- _Regression: No

## R1242
- _Time [hr]: 0.3

## R1243
- _Test environment: Lab-Car (auto)

## STC-BDY02-1255

## R1245
- _Object type: Nominal Test

## R1246
- _Status: REVIEWED

## R1247: Dipped beam lamps status failure

## R1248
To confirm ZB1 shall raise DTC when dipped beam lamp status failure

## R1249
- _Procedure: 1.Set NIgnitionStatus >= 0x05
  2.ZA1 receiver dipped beam lamps status failure signal from HeadLamp LIN, HeadLampsLIN::BStat_L_Failed == Failed ||
  HeadLampsLIN::BStat_R_Failed == Failed

## R1250
- _Pass criteria: ZA1 shall Raise DTC,
  NLHDippedBeamLampActiveSts = Fault ||
  NRHDippedBeamLampActiveSts = Fault

## R1251
- _Regression: No

## R1252
- _Time [hr]: 0.1

## R1253
- _Test environment: Lab-Car (auto)

## STC-BDY02-1448

## R1255
- _Object type: Nominal Test

## R1256
- _Status: REVIEWED

## R1257: Dipped beam lamps status failure error recovery

## R1258
To confirm DTC Shall clear when dipped beam lamp status failure error has cleared

## R1259
- _Procedure: 1.Set NIgnitionStatus >= 0x05
  2.Activate Dipped beam lamp status error:
  HeadLampsLIN::BStat_L_Failed == Failed ||
  HeadLampsLIN::BStat_R_Failed == Failed
  3.Recover dipped beam status error:
  Send valid LIN message for 10 consecutive frames,
  HeadLampsLIN::BStat_L_Failed == OK ||
  HeadLampsLIN::BStat_R_Failed == OK

## R1260
- _Pass criteria: ZA1 shall clear DTC,
  NLHDippedBeamLampActiveSts = OK ||
  NRHDippedBeamLampActiveSts = OK

## R1261
- _Regression: No

## R1262
- _Time [hr]: 0.1

## R1263
- _Test environment: Lab-Car (auto)

## STC-BDY02-1449

## R1265
- _Object type: Nominal Test

## R1266
- _Status: REVIEWED

## R1267: Dipped Beam lamp Communications Failure

## R1268
To confirm ZB1 Shall raise DTC when Dipped beam lamps communication failed

## R1269
- _Procedure: 1.Set NIgnitionStatus >= 0x05
  2.ZA1 receive Dipped beam lamps communication failure on HeadLamp LIN,
  HeadLampsLIN::BCOM_L_Failed == Failed ||
  HeadLampsLIN::BCOM_R_Failed == Failed

## R1270
- _Pass criteria: ZA1 Shall Raise DTC
  NLHDippedBeamLampActiveSts = Fault ||
  NRHDippedBeamLampActiveSts = Fault

## R1271
- _Regression: No

## R1272
- _Time [hr]: 0.1

## R1273
- _Test environment: Lab-Car (auto)

## STC-BDY02-1450

## R1275
- _Object type: Nominal Test

## R1276
- _Status: REVIEWED

## R1277: Dipped Beam lamp Communications Failure error recovery

## R1278
To confirm DTC Shall clear when Dipped beam lamps communication failed error has cleared

## R1279
- _Procedure: 1.Set NIgnitionStatus >= 0x05
  2.Activate Dipped beam Communications Failure:
  HeadLampsLIN::BCOM_L_Failed == Failed ||
  HeadLampsLIN::BCOM_R_Failed == Failed
  3.Recover dipped beam Communications Failure:
  Send valid LIN message for 10 consecutive frames,
  HeadLampsLIN::BCOM_L_Failed == OK ||
  HeadLampsLIN::BCOM_R_Failed == OK

## R1280
- _Pass criteria: NLHDippedBeamLampActiveSts = OK ||
  NRHDippedBeamLampActiveSts = OK

## R1281
- _Regression: No

## R1282
- _Time [hr]: 0.1

## R1283
- _Test environment: Lab-Car (auto)

## STC-BDY02-1451

## R1285
- _Object type: Nominal Test

## R1286
- _Status: REVIEWED

## R1287: Dipped beam Thermal failure or FAN in the Lamp failure

## R1288
To confirm ZB1 shall set DTC when Dipped beam Thermal failure or FAN in the Lamp failure

## R1289
- _Procedure: 1.Set NIgnitionStatus >= 0x05
  2.ZB1 receive Dipped beam Thermal failure or FAN in the Lamp failure on HeadLamp LIN,
  HeadLampsLIN::BFAN_L_Failed == Failed ||
  HeadLampsLIN::BFAN_R_Failed == Failed

## R1290
- _Pass criteria: ZA1 shall Raise DTC
  NLHDippedBeamLampActiveSts = Fault ||
  NRHDippedBeamLampActiveSts = Fault

## R1291
- _Regression: No

## R1292
- _Time [hr]: 0.1

## R1293
- _Test environment: Lab-Car (auto)

## STC-BDY02-1452

## R1295
- _Object type: Nominal Test

## R1296
- _Status: REVIEWED

## R1297: Dipped beam Thermal failure or FAN in the Lamp failure error recovery

## R1298
To confirm DTC Shall clear Dipped beam Thermal failure or FAN in the Lamp failure error has cleared

## R1299
- _Procedure: 1.Set NIgnitionStatus >= 0x05
  2.Activate Dipped beam Thermal failure or FAN in the Lamp failure:
  HeadLampsLIN::BFAN_L_Failed == Failed ||
  HeadLampsLIN::BFAN_R_Failed == Failed
  3.Recover Dipped beam Thermal failure or FAN in the Lamp failure:
  Send valid LIN message for 10 consecutive frames,
  HeadLampsLIN::BFAN_L_Failed == OK ||
  HeadLampsLIN::BFAN_R_Failed == OK

## R1300
- _Pass criteria: NLHDippedBeamLampActiveSts = OK ||
  NRHDippedBeamLampActiveSts = OK

## R1301
- _Regression: No

## R1302
- _Time [hr]: 0.1

## R1303
- _Test environment: Lab-Car (auto)

## STC-BDY02-1453

## R1305
- _Object type: Nominal Test

## R1306
- _Status: REVIEWED

## R1307: Dipped Beam lamp Response Error

## R1308
To confirm ZB1 shall raise DTC when Dipped Beam lamp Response Error

## R1309
- _Procedure: 1.Set NIgnitionStatus >= 0x05
  2.ZB1 receive Dipped Beam lamp Response Error
  on HeadLamp LIN,
  HeadLampsLIN::BBLRResponseError == Error ||
  HeadLampsLIN::BBLLResponseError== Error

## R1310
- _Pass criteria: ZA1 shall Raise DTC
  NLHDippedBeamLampActiveSts = Fault ||
  NRHDippedBeamLampActiveSts = Fault

## R1311
- _Regression: No

## R1312
- _Time [hr]: 0.1

## R1313
- _Test environment: Lab-Car (auto)

## STC-BDY02-1454

## R1315
- _Object type: Nominal Test

## R1316
- _Status: REVIEWED

## R1317: Dipped Beam lamp Response Error recovery

## R1318
To confirm ZB1 shall clear DTC Dipped Beam lamp Response Error has cleared

## R1319
- _Procedure: 1.Set NIgnitionStatus >= 0x05
  2.Activate Dipped Beam lamp Response Error:
  HeadLampsLIN::BBLRResponseError == Error ||
  HeadLampsLIN::BBLLResponseError== Error
  3.Recover Dipped Beam lamp Response Error:
  Send valid LIN message for 10 consecutive frames,
  HeadLampsLIN::BBLRResponseError == No Error ||
  HeadLampsLIN::BBLLResponseError== No Error

## R1320
- _Pass criteria: NLHDippedBeamLampActiveSts = OK ||
  NRHDippedBeamLampActiveSts = OK

## R1321
- _Regression: No

## R1322
- _Time [hr]: 0.1

## R1323
- _Test environment: Lab-Car (auto)

## STC-BDY02-1455

## R1325
- _Object type: Nominal Test

## R1326
- _Status: REVIEWED

## R1327: Dipped Beam Power Supply of the lamp is Too Low

## R1328
To confirm ZB1 shall raise DTC Dipped Beam Power Supply of the lamp is Too Low

## R1329
- _Procedure: 1.Set NIgnitionStatus >= 0x05
  2.ZB1 receive Dipped Beam Power Supply of the lamp is Too Low on HeadLamp LIN,
  HeadLampsLIN::BPowerSupply_L == Too Low ||
  HeadLampsLIN::BPowerSupply_R== Too Low

## R1330
- _Pass criteria: ZA1 shall Raise DTC
  NLHDippedBeamLampActiveSts = Fault ||
  NRHDippedBeamLampActiveSts = Fault

## R1331
- _Regression: No

## R1332
- _Time [hr]: 0.1

## R1333
- _Test environment: Lab-Car (auto)

## STC-BDY02-1456

## R1335
- _Object type: Nominal Test

## R1336
- _Status: REVIEWED

## R1337: Dipped Beam Power Supply of the lamp is Too Low Error recovery

## R1338
To confirm ZB1 shall clear DTCDipped Beam Power Supply of the lamp is Too Low Error recovery

## R1339
- _Procedure: 1.Set NIgnitionStatus >= 0x05
  2.Dipped Beam Power Supply of the lamp is Too Low Error:
  HeadLampsLIN::BPowerSupply_L == Too Low ||
  HeadLampsLIN::BPowerSupply_R== Too Low
  3.Recover Dipped Beam Power Supply of the lamp is Too Low Error:
  Send valid LIN message for 10 consecutive frames,
  HeadLampsLIN::BPowerSupply_L == OK ||
  HeadLampsLIN::BPowerSupply_R== Ok

## R1340
- _Pass criteria: NLHDippedBeamLampActiveSts = OK ||
  NRHDippedBeamLampActiveSts = OK

## R1341
- _Regression: No

## R1342
- _Time [hr]: 0.1

## R1343
- _Test environment: Lab-Car (auto)

## STC-BDY02-1457

## R1345
- _Object type: Nominal Test

## R1346
- _Status: REVIEWED

## R1347: Dipped Beam open/short circuit failure

## R1348
To confirm ZB1 shall raise DTC when Dipped Beam open/short circuit failure

## R1349
- _Procedure: 1.Set NIgnitionStatus >= 0x05
  2.Create Open/Short ciruit failure of the Dipped beam lamps

## R1350
- _Pass criteria: ZB1 shall Raise DTC
  NLHDippedBeamLampActiveSts = Fault
  NRHDippedBeamLampActiveSts = Fault && NDippedBeamClusterMessage = Fault display on ICU

## R1351
- _Regression: No

## R1352
- _Time [hr]: 0.1

## R1353
- _Test environment: Lab-Car (auto)

## STC-BDY02-1458

## R1355
- _Object type: Nominal Test

## R1356
- _Status: REVIEWED

## R1357: Dipped Beam open/short circuit failure recovery

## R1358
To confirm ZB1 shall clear DTC when Dipped Beam open/short circuit failure Error recovery

## R1359
- _Procedure: 1.Set NIgnitionStatus >= 0x05
  2.Create Open/Short ciruit failure of the Dipped beam lamps, Drive feedback current out of normal operation range for debounce time
  3.Clear the fault:
  Drive feedback current within normal operation range for debounce time ||
  A new ignition cycle

## R1360
- _Pass criteria: NLHDippedBeamLampActiveSts = Inactive
  NRHDippedBeamLampActiveSts = Inactive && NDippedBeamClusterMessage = Fault display shall be cleared on ICU

## R1361
- _Regression: No

## R1362
- _Time [hr]: 0.1

## R1363
- _Test environment: Lab-Car (auto)

## STC-BDY02-1123

## R1365
- _Object type: Nominal Test

## R1366
- _Status: REVIEWED

## R1367: Side light function activation

## R1368
To confirm side light function activation in ignition state =0x05

## R1369
- _Procedure: 1.Set NIgnitionStatus = 0x05
  2.NMasterLightSwitchPosition == Side Light || Dipped Beam

## R1370
- _Pass criteria: NSideLightLeftStatus = Active NSideLightRightStatus = Active

## R1371
- _Regression: No

## R1372
- _Time [hr]: 0.1

## R1373
- _Test environment: Lab-Car (auto)

## STC-BDY02-1124

## R1375
- _Object type: Nominal Test

## R1376
- _Status: REVIEWED

## R1377: Side light function activation with AUTO function

## R1378
To confirm side light function activation with AUTO light activation

## R1379
- _Procedure: 1.Set NIgnitionStatus = 0x05 ||
  PowertrainStatus = Torque Available
  2.NMasterLightSwitchPosition == AUTO

## R1380
- _Pass criteria: NSideLightLeftStatus = Active NSideLightRightStatus = Active

## R1381
- _Regression: No

## R1382
- _Time [hr]: 0.1

## R1383
- _Test environment: Lab-Car (auto)

## STC-BDY02-1125

## R1385
- _Object type: Nominal Test

## R1386
- _Status: REVIEWED

## R1387: Side light function activation with dipped beam activation

## R1388
To confirm side light function activation with dipped beam activation

## R1389
- _Procedure: NMasterLightSwitchPosition == OFF || AUTO
  && (NDippedBeamLeftStatus = Active NDippedBeamRightStatus = Active)

## R1390
- _Pass criteria: NSideLightLeftStatus = Active NSideLightRightStatus = Active

## R1391
- _Regression: No

## R1392
- _Time [hr]: 0.1

## R1393
- _Test environment: Lab-Car (auto)

## STC-BDY02-1126

## R1395
- _Object type: Nominal Test

## R1396
- _Status: REVIEWED

## R1397: Side light function deactivation with ignition state

## R1398
To confirm side light function deactivation when ignition state !=0x05 || Powertrain Activation

## R1399
- _Procedure: 1.Set NIgnitionStatus = 0x05
  2.NMasterLightSwitchPosition == Side Light || Dipped Beam
  3.Set NIgnitionStatus !=0x05 || Powertrain Activation

## R1400
- _Pass criteria: NSideLightLeftStatus = InActive NSideLightRightStatus = InActive

## R1401
- _Regression: No

## R1402
- _Time [hr]: 0.1

## R1403
- _Test environment: Lab-Car (auto)

## STC-BDY02-1127

## R1405
- _Object type: Nominal Test

## R1406
- _Status: REVIEWED

## R1407: side & tail lamps illumination when side lights are activated

## R1408
To confirm side & tail lamps illumination when side lights are activated

## R1409
- _Procedure: Activate side light function(Set NIgnitionStatus = 0x05
  && NMasterLightSwitchPosition == Side Light || Dipped Beam)

## R1410
- _Pass criteria: BLH_SidelampPositionIndicator = Active
  BRH_SidelampPositionIndicator = Active
  NTailLightLeftStatus = Active
  NTailLightRightStatus = Active

## R1411
- _Regression: No

## R1412
- _Time [hr]: 0.1

## R1413
- _Test environment: Lab-Car (auto)

## STC-BDY02-1128

## R1415
- _Object type: Nominal Test

## R1416
- _Status: REVIEWED

## R1417: ISO symbol when side lights function is activated

## R1418
To confirm ISO symbol when side lights function is activated

## R1419
- _Procedure: 1.Activate side light function(Set NIgnitionStatus = 0x05
  && NMasterLightSwitchPosition == Side Light || Dipped Beam)
  2.Check ISO symbol

## R1420
- _Pass criteria: Driver Display side lights tell tale illuminated in DDP

## R1421
- _Regression: No

## R1422
- _Time [hr]: 0.3

## R1423
- _Test environment: Lab-Car (manual)

## STC-BDY02-228

## R1425
- _Object type: Nominal Test

## R1426
- _Status: REVIEWED

## R1427: Side Light control logic- Hazard ON

## R1428
Side light function shall be deactivated when hazard is active

## R1429
- _Procedure: 1.NHazardStatus = 0x0 && NIndicatorLStatus =0x0 && NIndicatorRStatus = 0x0
  2.Set ignition status ≥ 5 && Master Light Switch Position = 1 || 2
  3.Set NHazardStatus= 0x1
  4.Set NHazardStatus= 0x0

## R1430
- _Pass criteria: 2.Side lights active.
  NSideLightLeftStatus = (0x1) && NSideLightRightStatus = (0x1),
  NTailLightLeftStatus = (0x1) && NTailLightRightStatus = (0x1),
  NMasterLightStatus = (0x1)
  3.Side lights inactive.
  NSideLightLeftStatus = (0x0) && NSideLightRightStatus = (0x0),
  NMasterLightStatus = (0x1)
  NTailLightLeftStatus = (0x1) && NTailLightRightStatus = (0x1)
  4.Side lights active.
  NSideLightLeftStatus = (0x1) && NSideLightRightStatus = (0x1)

## R1431
- _Regression: Yes

## R1432
- _Time [hr]: 0.4

## R1433
- _Test environment: Lab-Car (auto)

## STC-BDY02-1131

## R1435
- _Object type: Nominal Test

## R1436
- _Status: REVIEWED

## R1437: Side light Short circuit fault

## R1438
To confirm Rear lights diagnostic strategy when short circuit fault occurs

## R1439
- _Procedure: 1.Creat Side light circuit fault i.e., short circuit fault
  2.After fault, make sure the drive feedback curent is out of normal operation thresholds

## R1440
- _Pass criteria: NLHFrontLampActiveSts = SideLampInactive
  NRHFrontLampActiveSts = SideLampInactive
  2.A DTC shall be raised
  3.NSideLightClusterMessage = Fault

## R1441
- _Regression: No

## R1442
- _Time [hr]: 0.1

## R1443
- _Test environment: Lab-Car (auto)

## STC-BDY02-1132

## R1445
- _Object type: Nominal Test

## R1446
- _Status: REVIEWED

## R1447: Side light open circuit fault

## R1448
To confirm Rear lights diagnostic strategy when open circuit fault occurs

## R1449
- _Procedure: 1.Creat Side light circuit fault i.e., open circuit fault
  2.After fault, make sure the drive feedback curent is out of normal operation thresholds

## R1450
- _Pass criteria: NLHFrontLampActiveSts = SideLampInactive
  NRHFrontLampActiveSts = SideLampInactive
  2.A DTC shall be raised
  3.NSideLightClusterMessage = Fault

## R1451
- _Regression: No

## R1452
- _Time [hr]: 0.1

## R1453
- _Test environment: Lab-Car (auto)

## STC-BDY02-1133

## R1455
- _Object type: Nominal Test

## R1456
- _Status: REVIEWED

## R1457: Side light circuit circuit fault reset

## R1458
To confirm Rear lights fault reset with new ignition cycle

## R1459
- _Procedure: 1.Creat Side light circuit fault i.e., Open circuit fault
  2.After fault, make sure the drive feedback curent is out of normal operation thresholds
  3.Start new ignition cycle

## R1460
- _Pass criteria: NLHFrontLampActiveSts = SideLampInactive
  NRHFrontLampActiveSts = SideLampInactive

## R1461
- _Regression: No

## R1462
- _Time [hr]: 0.1

## R1463
- _Test environment: Lab-Car (auto)

## STC-BDY02-1628

## R1465
- _Object type: Nominal Test

## R1466
- _Status: REVIEWED

## R1467: Approach Light Function Activation

## R1468
The Approach Event shall be activated when the vehicle gets unlocked and the entry lighting is enabled and the battery state of charge is not low.

## R1469
- _Procedure: Preconditions:
  NTEntryLighting != OFF &&
  NBatteryLowStateOfCharge == OK
  1. Vehicle Unlocked
  NVehicleLockStatus [PE Lock] or [RKE Lock] -
  2. Vehicle locked
  NVehicleLockStatus [PE Unlock] or [RKE Unlock]

## R1470
- _Pass criteria: 2. BApproachLightStatus = ON(0x1)
  NDippedBeamLeftStatus = ON
  NDippedBeamRightStatus = ON
  NSideLightLeftStatus = ON
  NSideLightRightStatus = ON
  NTailLightLeftStatus = ON
  NTailLightRightStatus = ON

## R1471
- _Regression: No

## R1472
- _Time [hr]: 0.2

## R1473
- _Test environment: Lab-Car (manual)

## STC-BDY02-1629

## R1475
- _Object type: Nominal Test

## R1476
- _Status: REVIEWED

## R1477: TApproachLightTimer

## R1478
The approach lighting function shall de-activated when RKE or PE Lock is detected or calibratable timer (TApproachLightTimer) expires.

## R1479
- _Procedure: BApproachLightStatus = ON &&
  NVehicleLockStatus == [PE Lock] or [RKE Lock]
  or
  Approach Light Function being activated for over than TApproachLightTimer

## R1480
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF

## R1481
- _Regression: No

## R1482
- _Time [hr]: 0.2

## R1483
- _Test environment: Lab-Car (manual)

## STC-BDY02-1630

## R1485
- _Object type: Nominal Test

## R1486
- _Status: REVIEWED

## R1487: Approach Light Function Deactivation (ignition status)

## R1488
The Approach Event shall be deactivated when Ignition State is greater than Ignition (0x5).

## R1489
- _Procedure: BApproachLightStatus = ON &&
  NIgnitionStatus > 0x5

## R1490
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF

## R1491
- _Regression: No

## R1492
- _Time [hr]: 0.2

## R1493
- _Test environment: Lab-Car (manual)

## STC-BDY02-1631

## R1495
- _Object type: Nominal Test

## R1496
- _Status: REVIEWED

## R1497: Approach Light Function Deactivation (battery status)

## R1498
The Approach Event shall be deactivated when the battery state of charge is low.

## R1499
- _Procedure: Preconditions:
  BApproachLightStatus = ON &&
  NBatteryLowStateOfCharge != OK
  Test:
  1. Lock the vehicle

## R1500
- _Pass criteria: Verify that:
  BApproachLightStatus = OFF
  NDippedBeamLeftStatus = OFF
  NDippedBeamRightStatus = OFF
  NSideLightLeftStatus = OFF
  NSideLightRightStatus = OFF
  NTailLightLeftStatus = OFF
  NTailLightRightStatus = OFF

## R1501
- _Regression: No

## R1502
- _Time [hr]: 0.2

## R1503
- _Test environment: Lab-Car (manual)

## STC-BDY02-1632

## R1505
- _Object type: Nominal Test

## R1506
- _Status: REVIEWED

## R1507: Approach Light Function Deactivation (entry light disabled)

## R1508
The Approach Event shall be deactivated when the entry lighting is disabled on central display.

## R1509
- _Procedure: Preconditions:
  BApproachLightStatus = ON &&
  NTEntryLighting == OFF
  Test:
  1. Lock the vehicle

## R1510
- _Pass criteria: Verify that:
  BApproachLightStatus = OFF
  NDippedBeamLeftStatus = OFF
  NDippedBeamRightStatus = OFF
  NSideLightLeftStatus = OFF
  NSideLightRightStatus = OFF
  NTailLightLeftStatus = OFF
  NTailLightRightStatus = OFF

## R1511
- _Regression: No

## R1512
- _Time [hr]: 0.2

## R1513
- _Test environment: Lab-Car (manual)

## STC-BDY02-1633

## R1515
- _Object type: Nominal Test

## R1516
- _Status: REVIEWED

## R1517: Approach Light Function Deactivation (entry lighting timer)

## R1518
The Approach Event shall be deactivated when the entry lighting timer is reached.

## R1519
- _Procedure: BApproachLightStatus = ON &&
  NTEntryLighting timer reached

## R1520
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF

## R1521
- _Regression: No

## R1522
- _Time [hr]: 0.2

## R1523
- _Test environment: Lab-Car (manual)

## STC-BDY02-1634

## R1525
- _Object type: Nominal Test

## R1526
- _Status: REVIEWED

## R1527: Approach Light Function Deactivation (ADI comm fault)

## R1528
The Approach Event shall be deactivated when ADI communication is in fault

## R1529
- _Procedure: BApproachLightStatus = ON &&
  ADI communication fault raised

## R1530
- _Pass criteria: BApproachLightStatus = OFF
  NDippedBeamLeftStatus = OFF
  NDippedBeamRightStatus = OFF
  NSideLightLeftStatus = OFF
  NSideLightRightStatus = OFF
  NTailLightLeftStatus = OFF
  NTailLightRightStatus = OFF

## R1531
- _Regression: No

## R1532
- _Time [hr]: 0.2

## R1533
- _Test environment: Lab-Car (manual)

## STC-BDY02-1461

## R1535
- _Object type: Cross Functional Test

## R1536
- _Status: REVIEWED

## R1537: Approach Light timer user config (ID: STC-CFG02-01-1150)

## R1538
To confirm Approach Light timer user config

## R1539
- _Procedure: 1.Activate approach light function:
  NIgnitionStatus <= Awake &&
  NVehicleLockStatus == RKE Unlock
  2.Set TApproachLightTimer to different values using UserConfig settings from ADI:
  Reference SDS-CFG02-01-308

## R1540
- _Pass criteria: TApproachLightTimer: set to >10secs
  0x0 = OFF
  0x1 = 10 Seconds
  0x2 = 15 Seconds
  0x3 = 20 Seconds
  0x4 = 30 Seconds
  0x5 = 40 Seconds
  0x6 = 50 Seconds
  0x7 = 60 Seconds

## R1541
- _Regression: No

## R1542
- _Time [hr]: 0.2

## R1543
- _Test environment: Lab-Car (auto)

## STC-BDY02-375

## R1545
- _Object type: Cross Functional Test

## R1546
- _Status: REVIEWED

## R1547: Approach light user settings (ID:STC-CFG02-01-1150, STC-CFG02-01-1151, STC-CFG02-01-1152)

## R1548
Approach light user settings using menu stalk and lighting timer

## R1549
- _Procedure: Set approach lighting timer as per below:
  NTEntryLighting Timer (
  )_x000D_
  f (0
  1 15
  30_x000D_3 45_x000D_4
  NMenuLStalkBackStatus, _x000D_NMenuLStalkForwardStatus
  NMenuLStalkDownStatus,_x000D_NMenuLStalkUpStatus

## R1550
- _Pass criteria: NDippedBeamLeftStatus && NDippedBeamRightStatus shall follow the approach light timer and shall deactivate when timer expires

## R1551
- _Regression: Yes

## R1552
- _Time [hr]: 0.5

## R1553
- _Test environment: Lab-Car (manual)

## STC-BDY02-1635

## R1555
- _Object type: Nominal Test

## R1556
- _Status: REVIEWED

## R1557: Approach Event lighting function timer configuration

## R1558
The Approach Event lighting function timer shall be able to be configured by the user via Menu Stalk or contact screen

## R1559
- _Procedure: Check the central display and chenge the entry light time configuraion

## R1560
- _Pass criteria: NTEntryLighting value changes according to the central display settings

## R1561
- _Regression: No

## R1562
- _Time [hr]: 0.1

## R1563
- _Test environment: Lab-Car (manual)

## STC-BDY02-475

## R1565
- _Object type: Nominal Test

## R1566
- _Status: REVIEWED

## R1567: See You Home activation

## R1568
See You Home activation

## R1569
- _Procedure:
  1. Set Ignition State = 2
  2. Lock the car using RKE keys

## R1570
- _Pass criteria:
  1. BSeeYouHomeStatus = ON
  & Dipped Beam ON,
  NDippedBeamLeftStatus = (0x1) && NDippedBeamRightStatus = (0x1)

## R1571
- _Regression: Yes

## R1572
- _Time [hr]: 0.5

## R1573
- _Test environment: Lab-Car (auto)

## STC-BDY02-539

## R1575
- _Object type: Nominal Test

## R1576
- _Status: REVIEWED

## R1577: See You Home Activation

## R1578
See You Home Activation when Left door transition to Open and timer > 0

## R1579
- _Procedure: 1.Set NIgnitionStatus=2
  2.Set Timer Signal different from "OFF", NSeeYouHomeTimer >0 ||
  NTExitLighting >0
  3.VehicleLock Status == RKE Locked || PE Locked

## R1580
- _Pass criteria: BSeeYouHomeStatus = ON

## R1581
- _Regression: Yes

## R1582
- _Time [hr]: 0.4

## R1583
- _Test environment: Lab-Car (auto)

## STC-BDY02-548

## R1585
- _Object type: Nominal Test

## R1586
- _Status: REVIEWED

## R1587: See You Home Activation

## R1588
See You Home Activation when Right door transition to Open and timer > 0

## R1589
- _Procedure: 1.Set NIgnitionStatus=2
  2.Set Timer Signal different from "OFF", NSeeYouHomeTimer >0 ||
  NTExitLighting >0
  3.VehicleLock Status == RKE Locked || PE Locked

## R1590
- _Pass criteria: BSeeYouHomeStatus = ON

## R1591
- _Regression: Yes

## R1592
- _Time [hr]: 0.4

## R1593
- _Test environment: Lab-Car (auto)

## STC-BDY02-549

## R1595
- _Object type: Negative Test

## R1596
- _Status: REVIEWED

## R1597: See You Home deactivation with Right door open when timer=0

## R1598
See You Home deactivation when Right door transition to Open and timer = OFF

## R1599
- _Procedure: 1.Set NIgnitionStatus=2
  2.Set Timer Signal to "OFF", NSeeYouHomeTimer = 0 ||
  NTExitLighting = 0
  3.Right door transitions to an Open status, NDoorROpenStatus = 1

## R1600
- _Pass criteria: CUHomeActive= False and Dipped Beam=OFF

## R1601
- _Regression: No

## R1602
- _Time [hr]: 0.4

## R1603
- _Test environment: Lab-Car (auto)

## STC-BDY02-550

## R1605
- _Object type: Negative Test

## R1606
- _Status: REVIEWED

## R1607: See You Home deactivation with Left door open when timer=0

## R1608
See You Home deactivation when Left door transition to Open and timer = OFF

## R1609
- _Procedure: 1.Set NIgnitionStatus=2
  2.Set Timer Signal to "OFF", NSeeYouHomeTimer = 0 ||
  NTExitLighting = 0
  3.Left door transitions to an Open status, NDoorLOpenStatus = 1

## R1610
- _Pass criteria: CUHomeActive= False and Dipped Beam=OFF

## R1611
- _Regression: No

## R1612
- _Time [hr]: 0.4

## R1613
- _Test environment: Lab-Car (auto)

## STC-BDY02-551

## R1615
- _Object type: Nominal Test

## R1616
- _Status: REVIEWED

## R1617: See You Home deactivation with ignition state transition to 1

## R1618
See You Home deactivation when ignition state transition to 1 from 2 while CUHome is Active

## R1619
- _Procedure: 1.Activate See You Home:
  NIgnitionStatus == Awake &&
  (VehicleLock Status == RKE Locked || PE Locked) &&
  TSeeYouHomeTimer > 0
  2.Do Igniton state transition from 2 to 1, NIgnitionStatus = 1 within timer expires

## R1620
- _Pass criteria: 1.CUHomeActive= True and Dipped Beam=ON
  2.CUHomeActive= False and Dipped Beam=OFF

## R1621
- _Regression: No

## R1622
- _Time [hr]: 0.3

## R1623
- _Test environment: Lab-Car (auto)

## STC-BDY02-552

## R1625
- _Object type: Nominal Test

## R1626
- _Status: REVIEWED

## R1627: See You Home deactivation with ignition state transition >2

## R1628
See You Home deactivation when ignition state transition >2 while CUHome is Active

## R1629
- _Procedure: 1.Activate See You Home:
  NIgnitionStatus == Awake &&
  (VehicleLock Status == RKE Locked || PE Locked) &&
  TSeeYouHomeTimer > 0
  2.Set NIgnitionStatus > 2 within timer expiration

## R1630
- _Pass criteria: 1.CUHomeActive= True and Dipped Beam=ON
  2.CUHomeActive= False and Dipped Beam=OFF

## R1631
- _Regression: No

## R1632
- _Time [hr]: 0.3

## R1633
- _Test environment: Lab-Car (auto)

## STC-BDY02-553

## R1635
- _Object type: Nominal Test

## R1636
- _Status: REVIEWED

## R1637: See You Home deactivation when Car is locked then unlocked again

## R1638
See You Home deactivation when Car is locked then unlocked again while CUHome is Active

## R1639
- _Procedure: 1.Activate See You Home:
  NIgnitionStatus == Awake &&
  (VehicleLock Status == RKE Locked || PE Locked) &&
  TSeeYouHomeTimer > 0
  2.Lock the vehicle and then unlock again within timer expiration

## R1640
- _Pass criteria: 1.CUHomeActive= True and Dipped Beam=ON
  2.CUHomeActive= False and Dipped Beam=OFF

## R1641
- _Regression: No

## R1642
- _Time [hr]: 0.3

## R1643
- _Test environment: Lab-Car (auto)

## STC-BDY02-554

## R1645
- _Object type: Nominal Test

## R1646
- _Status: REVIEWED

## R1647: See You Home deactivation when Car is locked and the Timer expired

## R1648
See You Home deactivation when Car is locked and the Timer expired while CUHome is Active

## R1649
- _Procedure: 1.Activate See You Home:
  NIgnitionStatus == Awake &&
  (VehicleLock Status == RKE Locked || PE Locked) &&
  TSeeYouHomeTimer > 0
  2.Lock the vehicle and wait till timer expires

## R1650
- _Pass criteria: 1.CUHomeActive= True and Dipped Beam=ON
  2.CUHomeActive= False and Dipped Beam=OFF

## R1651
- _Regression: No

## R1652
- _Time [hr]: 0.3

## R1653
- _Test environment: Lab-Car (auto)

## STC-BDY02-1463

## R1655
- _Object type: Nominal Test

## R1656
- _Status: REVIEWED

## R1657: See You Home deactivation when vehicle is unlocked

## R1658
See You Home deactivation when vehicle is unlocked(RKE Unlock or PE Unlock) before timeout

## R1659
- _Procedure: 1.Activate See You Home:
  NIgnitionStatus == Awake &&
  (VehicleLock Status == RKE Locked || PE Locked) &&
  TSeeYouHomeTimer > 0
  2.Lock the vehicle, NVehicleLockStatus == RKE Unlock || PE Unlock

## R1660
- _Pass criteria: BSeeYouHomeStatus = OFF (0x0)

## R1661
- _Regression: No

## R1662
- _Time [hr]: 0.1

## R1663
- _Test environment: Lab-Car (auto)

## STC-BDY02-1464

## R1665
- _Object type: Nominal Test

## R1666
- _Status: REVIEWED

## R1667: See You Home deactivation when calibratable timer expires

## R1668
See You Home deactivation when calibratable timer expires

## R1669
- _Procedure: 1.Activate See You Home:
  NIgnitionStatus == Awake &&
  (VehicleLock Status == RKE Locked || PE Locked) &&
  TSeeYouHomeTimer > 0
  2.Wait until the calibration timer expires, TSeeYouHomeTimer == 0

## R1670
- _Pass criteria: BSeeYouHomeStatus = OFF (0x0)

## R1671
- _Regression: No

## R1672
- _Time [hr]: 0.2

## R1673
- _Test environment: Lab-Car (auto)

## STC-BDY02-555

## R1675
- _Object type: Nominal Test

## R1676
- _Status: REVIEWED

## R1677: See You Home Temporarily Time

## R1678
See You Home Temporarily time activation

## R1679
- _Procedure: 1.Set NIgnitionStatus = 2
  2.Pull DI Stalk towards the user, NFlashMainSwitch= 0x1
  3.Lock the vehicle using RKE lock button, NVehicleLockStatus = 0x5
  4.Set See You Home Temporarily Time not equal to OFF,
  NSeeYouHomeTimer !=0

## R1680
- _Pass criteria: See You Home Lighting shall be activated for See You Home Temporarily Time.
  CUHomeTimer = NSeeYouHomeTimer
  See You Home Fixed
  e_x000D_See You Home Temporarily Time Timer (se
  )_x000D_
  f (0
  1 15
  30_x000D_3 45

## R1681
- _Regression: No

## R1682
- _Time [hr]: 0.3

## R1683
- _Test environment: Lab-Car (auto)

## STC-BDY02-556

## R1685
- _Object type: Nominal Test

## R1686
- _Status: REVIEWED

## R1687: See You Home Temporarily Time

## R1688
See You Home Temporarily time activation

## R1689
- _Procedure: 1.Set NIgnitionStatus = 2
  2.Pull DI Stalk towards the user, NFlashMainSwitch= 0x1
  3.Lock the vehicle using PE lock button, (NVehicleLockStatus == RKE Lock || PE Lock)
  4.Set See You Home Temporarily Time not equal to OFF, NSeeYouHomeTimer >0 || NTExitLighting >0

## R1690
- _Pass criteria: See You Home Lighting shall be activated for See You Home Temporarily Time.
  CUHomeTimer = NSeeYouHomeTimer
  See You Home Fixed
  e_x000D_See You Home Temporarily Time Timer (se
  )_x000D_
  f (0
  1 15
  30_x000D_3 45

## R1691
- _Regression: Yes

## R1692
- _Time [hr]: 0.3

## R1693
- _Test environment: Lab-Car (auto)

## STC-BDY02-558

## R1695
- _Object type: Nominal Test

## R1696
- _Status: REVIEWED

## R1697: See You Home Temporarily Time shall take precedence over the See You Home Fixed Time

## R1698
See You Home Temporarily Time shall take precedence over the See You Home Fixed Time when NSeeYouHomeTimer !=0

## R1699
- _Procedure: 1.Set NIgnitionStatus = 2
  2.Set See You Home Temporarily Time not equal to OFF,
  NSeeYouHomeTimer !=0 (NTExitLighting !=0)
  3.Lock the vehicle (RKE or PE lock (NVehicleLockStatus = 0x5 || 0x6)
  4.Pull the DI Stalk, NFlashMainSwitch= 0x1 before timer expires

## R1700
- _Pass criteria: 3. TSeeYouHomeTimer = CUHomeTempTime
  4. See You Home Lighting function activated

## R1701
- _Regression: Yes

## R1702
- _Time [hr]: 0.4

## R1703
- _Test environment: Lab-Car (auto)

## STC-BDY02-477

## R1705
- _Object type: Nominal Test

## R1706
- _Status: REVIEWED

## R1707: See You Home Lighting timer

## R1708
See You Home Lighting timer user configuration

## R1709
- _Procedure:
  1. Configure See You Home Lighting timer through the Menu on the driver display using the Menu stalk [ UserConfig::NTExitLighting]
  NTExitLighting Timer (
  )_x000D_
  f (0
  1 15
  30_x000D_3 45

## R1710
- _Pass criteria: See you home lighting i.e., Dipped beam ON duration shall follow the NSeeYouHomeTimer

## R1711
- _Regression: No

## R1712
- _Time [hr]: 0.5

## R1713
- _Test environment: Lab-Car (auto)

## STC-BDY02-1465

## R1715
- _Object type: Nominal Test

## R1716
- _Status: REVIEWED

## R1717: See You Home Temporarily Time increment

## R1718
See You Home Temporarily Time increment using DIMS stalk

## R1719
- _Procedure: 1.NIgnitionStatus == Awake
  2.Pull DIMS stalk towards the steering wheel to a momentary position - first time
  3.Pull DIMS stalk towards the steering wheel to a momentary position - second time
  4.Pull DIMS stalk towards the steering wheel to a momentary position - more than three times

## R1720
- _Pass criteria: Default:
  CUHomeTempTime = 15 Seconds
  Pull Flash first time:
  CUHomeTempTime = 30 Seconds
  Pull Flash second time:
  CUHomeTempTime = 45 Seconds
  Pull Flash more than three times:
  CUHomeTempTime = 60 Seconds

## R1721
- _Regression: No

## R1722
- _Time [hr]: 0.1

## R1723
- _Test environment: Lab-Car (auto)

## STC-BDY02-1611

## R1725
- _Object type: Nominal Test

## R1726
- _Status: REVIEWED

## R1727: Welcome Event activation

## R1728
Welcome event activation when the vehicle is locked, the passive entry is enable, the keyfob is detected to enter Welcome Zone, the entry lighting is enabled and the battery state of charge is not low

## R1729
- _Procedure: BWelcomeEventActive == ON &&
  NTEntryLighting != OFF &&
  NignitionState == LOCKED &&
  NBatteryLowStateOfCharge == OK

## R1730
- _Pass criteria: BWelcomeEventStatus = ON
  NSideLightLeftStatus = ON
  NSideLightRightStatus = ON
  NTailLightLeftStatus = ON
  NTailLightRightStatus = ON

## R1731
- _Regression: No

## R1732
- _Time [hr]: 0.4

## R1733
- _Test environment: Lab-Car (auto)

## STC-BDY02-1612

## R1735
- _Object type: Nominal Test

## R1736
- _Status: REVIEWED

## R1737: Welcome Event deactivation

## R1738
Welcome event deactivation when Ignition State is greater than Awake (0x2)

## R1739
- _Procedure: BWelcomeEventStatus == ON &&
  NignitionState >= Awake

## R1740
- _Pass criteria: BWelcomeEventStatus = OFF
  NSideLightLeftStatus = OFF
  NSideLightRightStatus = OFF
  NTailLightLeftStatus = OFF
  NTailLightRightStatus = OFF

## R1741
- _Regression: No

## R1742
- _Time [hr]: 0.4

## R1743
- _Test environment: Lab-Car (auto)

## STC-BDY02-1613

## R1745
- _Object type: Nominal Test

## R1746
- _Status: REVIEWED

## R1747: Welcome Event deactivation

## R1748
Welcome event deactivation when the battery state of charge is low

## R1749
- _Procedure: BWelcomeEventStatus == ON &&
  NBatteryLowStateOfCharge != OK

## R1750
- _Pass criteria: BWelcomeEventStatus = OFF
  NSideLightLeftStatus = OFF
  NSideLightRightStatus = OFF
  NTailLightLeftStatus = OFF
  NTailLightRightStatus = OFF

## R1751
- _Regression: No

## R1752
- _Time [hr]: 0.4

## R1753
- _Test environment: Lab-Car (auto)

## STC-BDY02-1614

## R1755
- _Object type: Nominal Test

## R1756
- _Status: REVIEWED

## R1757: Welcome Event deactivation

## R1758
Welcome Event deactivation when the keyfob is detected to exit Welcome Zone or to stay in Welcome Zone over a timeout

## R1759
- _Procedure: BWelcomeEventStatus == ON &&
  BWelcomeEventActive == OFF

## R1760
- _Pass criteria: BWelcomeEventStatus = OFF
  NSideLightLeftStatus = OFF
  NSideLightRightStatus = OFF
  NTailLightLeftStatus = OFF
  NTailLightRightStatus = OFF

## R1761
- _Regression: No

## R1762
- _Time [hr]: 0.4

## R1763
- _Test environment: Lab-Car (auto)

## STC-BDY02-1615

## R1765
- _Object type: Nominal Test

## R1766
- _Status: REVIEWED

## R1767: Welcome Event deactivation

## R1768
Welcome Event deactivation when ADI communication is in fault

## R1769
- _Procedure: BWelcomeEventStatus == ON &&
  ADI communication fault raised

## R1770
- _Pass criteria: BWelcomeEventStatus = OFF
  NSideLightLeftStatus = OFF
  NSideLightRightStatus = OFF
  NTailLightLeftStatus = OFF
  NTailLightRightStatus = OFF

## R1771
- _Regression: No

## R1772
- _Time [hr]: 0.4

## R1773
- _Test environment: Lab-Car (manual)

## STC-BDY02-1616

## R1775
- _Object type: Nominal Test

## R1776
- _Status: REVIEWED

## R1777: Sign Off Event activation

## R1778
Sign Off Event activation when the door gets open after Ignition State drops to Awake, the exit lighting is enabled and the battery state of charge is not low

## R1779
- _Procedure: BSignOffEventActive == ON &&
  NTExitLighting != OFF &&
  NBatteryLowStateOfCharge == OK

## R1780
- _Pass criteria: BSignOffEventStatus = ON
  NDippedBeamLeftStatus = ON
  NDippedBeamRightStatus = ON
  NSideLightLeftStatus = ON
  NSideLightRightStatus = ON
  NTailLightLeftStatus = ON
  NTailLightRightStatus = ON

## R1781
- _Regression: Yes

## R1782
- _Time [hr]: 0.1

## R1783
- _Test environment: Lab-Car (auto)

## STC-BDY02-1618

## R1785
- _Object type: Nominal Test

## R1786
- _Status: REVIEWED

## R1787: Sign Off Event deactivation

## R1788
Sign Off Event deactivation when Ignition State transits back to Awake above with door closed or keyfob enters back to Welcome Zone or vehicle gets unlock from lock again

## R1789
- _Procedure: BSignOffEventStatus = ON &&
  BSignOffEventActive == OFF

## R1790
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF

## R1791
- _Regression: Yes

## R1792
- _Time [hr]: 0.1

## R1793
- _Test environment: Lab-Car (auto)

## STC-BDY02-1619

## R1795
- _Object type: Nominal Test

## R1796
- _Status: REVIEWED

## R1797: Sign Off Event deactivation

## R1798
Sign Off Event deactivation when the battery state of charge is low

## R1799
- _Procedure: BSignOffEventStatus = ON &&
  NBatteryLowStateOfCharge != OK

## R1800
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF

## R1801
- _Regression: Yes

## R1802
- _Time [hr]: 0.1

## R1803
- _Test environment: Lab-Car (auto)

## STC-BDY02-1620

## R1805
- _Object type: Nominal Test

## R1806
- _Status: REVIEWED

## R1807: Sign Off Event deactivation

## R1808
Sign Off Event deactivation when the exit lighting is disable on central display

## R1809
- _Procedure: BSignOffEventStatus = ON &&
  NTExitLighting == OFF

## R1810
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF

## R1811
- _Regression: Yes

## R1812
- _Time [hr]: 0.1

## R1813
- _Test environment: Lab-Car (auto)

## STC-BDY02-1621

## R1815
- _Object type: Nominal Test

## R1816
- _Status: REVIEWED

## R1817: Sign Off Event deactivation

## R1818
Sign Off Event deactivation when the exit lighting timer is reached

## R1819
- _Procedure: BSignOffEventStatus = ON &&
  NTExitLighting timer reached

## R1820
- _Pass criteria: BSignOffEventStatus = OFF
  NDippedBeamLeftStatus = OFF
  NDippedBeamRightStatus = OFF
  NSideLightLeftStatus = OFF
  NSideLightRightStatus = OFF
  NTailLightLeftStatus = OFF
  NTailLightRightStatus = OFF

## R1821
- _Regression: Yes

## R1822
- _Time [hr]: 0.1

## R1823
- _Test environment: Lab-Car (auto)

## STC-BDY02-1622

## R1825
- _Object type: Nominal Test

## R1826
- _Status: REVIEWED

## R1827: Sign Off Event lighting function timer

## R1828
Sign Off Event lighting function timer shall be able to be configured by the user via Menu Stalk or contact screen

## R1829
- _Procedure: Central display exit lighting settings

## R1830
- _Pass criteria: NTExitLighting

## R1831
- _Regression: Yes

## R1832
- _Time [hr]: 0.1

## R1833
- _Test environment: Vehicle (static)

## STC-BDY02-1623

## R1835
- _Object type: Nominal Test

## R1836
- _Status: REVIEWED

## R1837: Sign Off Event lighting function activation

## R1838
Sign Off Event lighting function activation when the DI Stalk is pulled towards the user, the door gets open after ignition state drops to Awake and the battery state of charge is not low

## R1839
- _Procedure: BSignOffEventActive == ON &&
  NFlashMainSwitch == Latched &&
  NBatteryLowStateOfCharge == OK

## R1840
- _Pass criteria: BSignOffEventStatus = ON
  NDippedBeamLeftStatus = ON
  NDippedBeamRightStatus = ON
  NSideLightLeftStatus = ON
  NSideLightRightStatus = ON
  NTailLightLeftStatus = ON
  NTailLightRightStatus = ON

## R1841
- _Regression: Yes

## R1842
- _Time [hr]: 0.1

## R1843
- _Test environment: Lab-Car (auto)

## STC-BDY02-1624

## R1845
- _Object type: Nominal Test

## R1846
- _Status: REVIEWED

## R1847: Exit lighting timer

## R1848
The default exit lighting timer shall be 15s and be able to increase by 15s up to 60s maximum every time when pulling the DI stalk towards the steering wheel to a momentary position with Ignition state on Awake (0x2).

## R1849
- _Procedure: NIgnitionStatus == Awake &&
  NFlashMainSwitch == Flash

## R1850
- _Pass criteria: NTExitLighting starts from 15s and increases by 15s up to 60s

## R1851
- _Regression: Yes

## R1852
- _Time [hr]: 0.1

## R1853
- _Test environment: Vehicle (static)

## STC-BDY02-1625

## R1855
- _Object type: Nominal Test

## R1856
- _Status: REVIEWED

## R1857: Sign Off Event deactivation

## R1858
Sign Off Event deactivation when ADI communication is in fault

## R1859
- _Procedure: BSignOffEventActive == ON &&
  ADI communication fault raised

## R1860
- _Pass criteria: BSignOffEventActive = OFF
  NDippedBeamLeftStatus = OFF
  NDippedBeamRightStatus = OFF
  NSideLightLeftStatus = OFF
  NSideLightRightStatus = OFF
  NTailLightLeftStatus = OFF
  NTailLightRightStatus = OFF

## R1861
- _Regression: No

## R1862
- _Time [hr]: 0.1

## R1863
- _Test environment: Vehicle (static)

## STC-BDY02-1138

## R1865
- _Object type: Nominal Test

## R1866
- _Status: REVIEWED

## R1867: DTRL deactivation with ignition state

## R1868
To confirm DTRL deactivation when ignition state < 5

## R1869
- _Procedure: 1.Set NIgnitionStatus == Ignition (0x5)
  2.Activate DTRL function(DTRL Function available
  && NMasterLightSwitchPosition == OFF && NDippedBeamLeftStatus == Inactive && NDippedBeamRightStatus == Inactive)
  3.Set NIgnitionStatus !== Ignition (0x5)

## R1870
- _Pass criteria: NDTRLLeftStatus = InActive NDTRLRightStatus = InActive

## R1871
- _Regression: No

## R1872
- _Time [hr]: 0.1

## R1873
- _Test environment: Lab-Car (auto)

## STC-BDY02-217

## R1875
- _Object type: Cross Functional Test

## R1876
- _Status: REVIEWED

## R1877: DTRL control logic - Right Indicator ON (ID:STC-HMI01-204)

## R1878
DTRL of the right hand shall be deactivated when right hand directional indicator is active

## R1879
- _Procedure: 1.NHazardStatus = 0x0 && NIndicatorLStatus =0x0 && NIndicatorRStatus = 0x0
  2.Set ignition status ≥ 5 && Master Light Switch Position = 0 || A
  3.Set NIndicatorRStatus = 0x1
  4.Set NIndicatorRStatus = 0x0

## R1880
- _Pass criteria: 2.DTRL is active.
  NDTRLLeftStatus = (0x1) && NDTRLRightStatus = (0x1),
  NTailLightLeftStatus = (0x1) && NTailLightRightStatus = (0x1),
  NMasterLightStatus = (0x1)
  3.DTRL of the left hand is inactive.
  NDTRLLeftStatus = (0x1) && NDTRLRightStatus = (0x0),
  NTailLightLeftStatus = (0x1) && NTailLightRightStatus = (0x1),NMasterLightStatus = (0x1)
  4.DTRL is active.
  NDTRLLeftStatus = (0x1) && NDTRLRightStatus = (0x1),NMasterLightStatus = (0x1)

## R1881
- _Regression: Yes

## R1882
- _Time [hr]: 0.2

## R1883
- _Test environment: Lab-Car (auto)

## STC-BDY02-225

## R1885
- _Object type: Nominal Test

## R1886
- _Status: REVIEWED

## R1887: DTRL control logic - Left Indicator ON

## R1888
DTRL of the left hand shall be deactivated when left hand directional indicator is active

## R1889
- _Procedure: 1.NHazardStatus = 0x0 && NIndicatorLStatus =0x0 && NIndicatorRStatus = 0x0
  2.Set ignition status ≥ 5 && Master Light Switch Position = 0 || A
  3.Set NIndicatorLStatus = 0x1
  4.Set NIndicatorLStatus = 0x0

## R1890
- _Pass criteria: 2.DTRL is active.
  NDTRLLeftStatus = (0x1) && NDTRLRightStatus = (0x1),
  NTailLightLeftStatus = (0x1) && NTailLightRightStatus = (0x1),
  NMasterLightStatus = (0x1)
  3.DTRL of the left hand is inactive.
  NDTRLLeftStatus = (0x0) && NDTRLRightStatus = (0x1),
  NMasterLightStatus = (0x1),
  NTailLightLeftStatus = (0x1) && NTailLightRightStatus = (0x1)
  4.DTRL is active.
  NDTRLLeftStatus = (0x1) && NDTRLRightStatus = (0x1),NMasterLightStatus = (0x1)

## R1891
- _Regression: Yes

## R1892
- _Time [hr]: 0.2

## R1893
- _Test environment: Lab-Car (auto)

## STC-BDY02-222

## R1895
- _Object type: Nominal Test

## R1896
- _Status: REVIEWED

## R1897: DTRL control logic - Hazard ON

## R1898
DTRL function shall be deactivated when hazard is active

## R1899
- _Procedure: 1.NHazardStatus = 0x0 && NIndicatorLStatus =0x0 && NIndicatorRStatus = 0x0
  2.Set ignition status ≥ 5 && Master Light Switch Position = 0 || A
  3.Set NHazardStatus= 0x1
  4.Set NHazardStatus= 0x0

## R1900
- _Pass criteria: 2.DTRL is active.
  NDTRLLeftStatus = (0x1) && NDTRLRightStatus = (0x1), NTailLightLeftStatus = (0x1) && NTailLightRightStatus = (0x1)
  3.DTRL is inactive.
  NDTRLLeftStatus = (0x0) && NDTRLRightStatus = (0x0),
  NMasterLightStatus = (0x1),
  NTailLightLeftStatus = (0x1) && NTailLightRightStatus = (0x1)
  4.DTRL is active.
  NDTRLLeftStatus = (0x1) && NDTRLRightStatus = (0x1)

## R1901
- _Regression: Yes

## R1902
- _Time [hr]: 0.2

## R1903
- _Test environment: Lab-Car (auto)

## STC-BDY02-1139

## R1905
- _Object type: Nominal Test

## R1906
- _Status: REVIEWED

## R1907: DTRL deactivation with MLS position

## R1908
To confirm DTRL deactivation when Master Light Switch Position is set to Side Light or Dipped Beam position

## R1909
- _Procedure: 1.Set NIgnitionStatus == Ignition (0x5)
  2.Activate DTRL function(DTRL Function available
  && NMasterLightSwitchPosition == OFF && NDippedBeamLeftStatus == Inactive && NDippedBeamRightStatus == Inactive)
  3.Set Master Light Switch Position is set to Side Light or Dipped Beam position

## R1910
- _Pass criteria: NDTRLLeftStatus = InActive NDTRLRightStatus = InActive

## R1911
- _Regression: No

## R1912
- _Time [hr]: 0.1

## R1913
- _Test environment: Lab-Car (auto)

## STC-BDY02-1137

## R1915
- _Object type: Nominal Test

## R1916
- _Status: REVIEWED

## R1917: side & tail lamps illumination when DTRL lights are activated

## R1918
To confirm side & tail lamps illumination when DTRL lights are activated

## R1919
- _Procedure: Activate DTRL function(DTRL Function available && NMasterLightSwitchPosition == AUTO
  && NRainLightLSignalError == no error && NLightSwitchRequest == ON && NLightSwitchReason == Daylight)

## R1920
- _Pass criteria: BLH_HeadlampLEDActivateReq = Active
  BRH_HeadlampLEDActivateReq = Active
  NTailLightLeftStatus = Active
  NTailLightRightStatus = Active

## R1921
- _Regression: No

## R1922
- _Time [hr]: 0.1

## R1923
- _Test environment: Lab-Car (auto)

## STC-BDY02-1142

## R1925
- _Object type: Nominal Test

## R1926
- _Status: REVIEWED

## R1927: DTRL Short circuit fault

## R1928
To confirm DTRL lights diagnostic strategy when short circuit fault occurs

## R1929
- _Procedure: 1.Creat DTRL circuit fault i.e., short circuit fault
  2.After fault, make sure the drive feedback curent is out of normal operation thresholds

## R1930
- _Pass criteria: NLHFrontLampActiveSts = DTRLLampInactive
  NRHFrontLampActiveSts = DTRLLampInactive
  2.A DTC shall be raised
  3.NDTRLClusterMessage = Fault

## R1931
- _Regression: No

## R1932
- _Time [hr]: 0.1

## R1933
- _Test environment: Lab-Car (auto)

## STC-BDY02-1143

## R1935
- _Object type: Nominal Test

## R1936
- _Status: REVIEWED

## R1937: DTRL open circuit fault

## R1938
To confirm DTRL lights diagnostic strategy when open circuit fault occurs

## R1939
- _Procedure: 1.Creat DTRL circuit fault i.e., open circuit fault
  2.After fault, make sure the drive feedback curent is out of normal operation thresholds

## R1940
- _Pass criteria: NLHFrontLampActiveSts = DTRLLampInactive
  NRHFrontLampActiveSts = DTRLLampInactive
  2.A DTC shall be raised
  3.NDTRLClusterMessage = Fault

## R1941
- _Regression: No

## R1942
- _Time [hr]: 0.1

## R1943
- _Test environment: Lab-Car (auto)

## STC-BDY02-1144

## R1945
- _Object type: Nominal Test

## R1946
- _Status: REVIEWED

## R1947: DTRL circuit circuit fault reset

## R1948
To confirm DTRL lights fault reset with new ignition cycle

## R1949
- _Procedure: 1.Creat DTRL circuit fault i.e., Open circuit fault
  2.After fault, make sure the drive feedback curent is out of normal operation thresholds
  3.Start new ignition cycle

## R1950
- _Pass criteria: NLHFrontLampActiveSts = DTRLLampInactive
  NRHFrontLampActiveSts = DTRLLampInactive

## R1951
- _Regression: No

## R1952
- _Time [hr]: 0.1

## R1953
- _Test environment: Lab-Car (auto)

## STC-BDY02-382

## R1955
- _Object type: Cross Functional Test

## R1956
- _Status: REVIEWED

## R1957: Side markers activation for SAE market (ID:STC-CFG01-01-337)

## R1958
Side markers activation when MLS= 1||2 for SAE market

## R1959
- _Procedure: 1.Set NVehicleMarket = USA || Canada
  2.Set NIgnitionStatus < 5
  3.Master Light Switch Position = 1 || 2

## R1960
- _Pass criteria: NFrontLeftSideMarkerActvReq = Active &&
  NRearLeftSideMarkerActvReq = Active &&
  NFrontRightSideMarkerActvReq = Active &&
  NRearRightSideMarkerActvReq = Active

## R1961
- _Regression: Yes

## R1962
- _Time [hr]: 0.1

## R1963
- _Test environment: Lab-Car (auto)

## STC-BDY02-1474

## R1965
- _Object type: Nominal Test

## R1966
- _Status: REVIEWED

## R1967: Side markers activation for SAE market

## R1968
Side markers activation when ign>=5 for SAE market

## R1969
- _Procedure: 1.Set NVehicleMarket = USA || Canada
  2.Set NIgnitionStatus == (Ignition (0x5) || Powertrain Activation (0x6))

## R1970
- _Pass criteria: NFrontLeftSideMarkerActvReq = Active &&
  NRearLeftSideMarkerActvReq = Active &&
  NFrontRightSideMarkerActvReq = Active &&
  NRearRightSideMarkerActvReq = Active

## R1971
- _Regression: Yes

## R1972
- _Time [hr]: 0.1

## R1973
- _Test environment: Lab-Car (auto)

## STC-BDY02-383

## R1975
- _Object type: Nominal Test

## R1976
- _Status: REVIEWED

## R1977: Side markers activation for ECE market

## R1978
Side markers activation with direction indicator function

## R1979
- _Procedure: 1.Set NVehicleMarket != (USA || Canada) && INIgnitionStatus ≥ 5
  Case 1:
  NRepeaterLeftOn == Active
  Case 2:
  NRepeaterRightOn == Active

## R1980
- _Pass criteria: Case 1:
  NFrontLeftSideMarkerActvReq = Active &&
  NRearLeftSideMarkerActvReq = Inactive
  Case 2:
  NFrontRightSideMarkerActvReq= Active &&
  NRearRightSideMarkerActvReq = Inactive

## R1981
- _Regression: Yes

## R1982
- _Time [hr]: 0.1

## R1983
- _Test environment: Lab-Car (auto)

## STC-BDY02-1147

## R1985
- _Object type: Nominal Test

## R1986
- _Status: REVIEWED

## R1987: Side marker Short circuit fault

## R1988
To confirm Side marker lights diagnostic strategy when short circuit fault occurs

## R1989
- _Procedure: 1.Creat Side marker circuit fault i.e., short circuit fault
  2.After fault, make sure the drive feedback curent is out of normal operation thresholds

## R1990
- _Pass criteria: NFrontLeftSideMarkerActiveStatus = Inactive
  NFrontRightSideMarkerActiveStatus = Inactive
  NRearLeftSideMarkerActiveStatus = Inactive
  NRearRightSideMarkerActiveStatus = Inactive
  2.A DTC shall be raised
  3.NSideMarkerClusterMessage = Fault

## R1991
- _Regression: No

## R1992
- _Time [hr]: 0.1

## R1993
- _Test environment: Lab-Car (auto)

## STC-BDY02-1148

## R1995
- _Object type: Nominal Test

## R1996
- _Status: REVIEWED

## R1997: Side marker open circuit fault

## R1998
To confirm Side marker lights diagnostic strategy when open circuit fault occurs

## R1999
- _Procedure: 1.Creat Side marker circuit fault i.e., open circuit fault
  2.After fault, make sure the drive feedback curent is out of normal operation thresholds

## R2000
- _Pass criteria: NFrontLeftSideMarkerActiveStatus = Inactive
  NFrontRightSideMarkerActiveStatus = Inactive
  NRearLeftSideMarkerActiveStatus = Inactive
  NRearRightSideMarkerActiveStatus = Inactive
  2.A DTC shall be raised
  3.NSideMarkerClusterMessage = Fault

## R2001
- _Regression: No

## R2002
- _Time [hr]: 0.1

## R2003
- _Test environment: Lab-Car (auto)

## STC-BDY02-1149

## R2005
- _Object type: Nominal Test

## R2006
- _Status: REVIEWED

## R2007: Side marker circuit circuit fault reset

## R2008
To confirm Side marker lights fault reset with new ignition cycle

## R2009
- _Procedure: 1.Creat Side marker circuit fault i.e., Open circuit fault
  2.After fault, make sure the drive feedback curent is out of normal operation thresholds
  3.Start new ignition cycle

## R2010
- _Pass criteria: NFrontLeftSideMarkerActiveStatus = Inactive
  NFrontRightSideMarkerActiveStatus = Inactive
  NRearLeftSideMarkerActiveStatus = Inactive
  NRearRightSideMarkerActiveStatus = Inactive

## R2011
- _Regression: No

## R2012
- _Time [hr]: 0.1

## R2013
- _Test environment: Lab-Car (auto)

## STC-BDY02-1476

## R2015
- _Object type: Nominal Test

## R2016
- _Status: REVIEWED

## R2017: Brake light activation

## R2018
To confirm brake lights activation with ignition

## R2019
- _Procedure: 1.Set NIgnitionStatus == PT Wake || Ignition || Powertrain Activation
  2.Press brake pedal:
  NBrakepedalStatus_Q == Valid && NBrakepedalStatus == Pressed

## R2020
- _Pass criteria: NBrakeLightLStatus = Active
  NBrakeLightRStatus = Active
  NBrakeLightMiddleStatus = Active

## R2021
- _Regression: Yes

## R2022
- _Time [hr]: 0.1

## R2023
- _Test environment: Lab-Car (auto)

## STC-BDY02-1478

## R2025
- _Object type: Nominal Test

## R2026
- _Status: REVIEWED

## R2027: Brake light activation

## R2028
To confirm brake lights activation when quality signal is Faulty

## R2029
- _Procedure: 1.Set NIgnitionStatus == PT Wake || Ignition || Powertrain Activation
  2.Brake pedal quality signal is Faulty and Press brake pedal,
  NBrakepedalStatus_Q != Valid && NpBrake_Q == Valid && pBrake >= pBrakeThresholdActive

## R2030
- _Pass criteria: NBrakeLightLStatus = Active
  NBrakeLightRStatus = Active
  NBrakeLightMiddleStatus = Active

## R2031
- _Regression: No

## R2032
- _Time [hr]: 0.1

## R2033
- _Test environment: Lab-Car (auto)

## STC-BDY02-1479

## R2035
- _Object type: Nominal Test

## R2036
- _Status: REVIEWED

## R2037: Brake light activation

## R2038
To confirm brake lights activation when quality signal and brake threshold both are Faulty

## R2039
- _Procedure: 1.Set NIgnitionStatus == PT Wake || Ignition || Powertrain Activation
  2.Brake pedal quality signal and brake threshold both are Faulty,
  NBrakepedalStatus_Q != Valid && NpBrake_Q != Valid

## R2040
- _Pass criteria: NBrakeLightLStatus = Active
  NBrakeLightRStatus = Active
  NBrakeLightMiddleStatus = Active

## R2041
- _Regression: No

## R2042
- _Time [hr]: 0.1

## R2043
- _Test environment: Lab-Car (auto)

## STC-BDY02-1151

## R2045
- _Object type: Nominal Test

## R2046
- _Status: REVIEWED

## R2047: Brake light activation with ESP request

## R2048
To confirm brake lights activation when ESP requested

## R2049
- _Procedure: 1.Set NIgnitionStatus == PT Wake || Ignition || Powertrain Activation
  2.ESP requests brake light illumination, NDynBrkActive == Active || NBrakeLightRequest == Active

## R2050
- _Pass criteria: Brake Light illumination shall be 100% pwm

## R2051
- _Regression: No

## R2052
- _Time [hr]: 0.1

## R2053
- _Test environment: Lab-Car (auto)

## STC-BDY02-1480

## R2055
- _Object type: Nominal Test

## R2056
- _Status: REVIEWED

## R2057: Brake light activation

## R2058
To confirm brake lights activation when ESP requested

## R2059
- _Procedure: 1.Set NIgnitionStatus == PT Wake || Ignition || Powertrain Activation
  2.Set NDynBrkActive == Active || NRWUActive == Active

## R2060
- _Pass criteria: NBrakeLightLStatus = Active
  NBrakeLightRStatus = Active
  NBrakeLightMiddleStatus = Active

## R2061
- _Regression: No

## R2062
- _Time [hr]: 0.1

## R2063
- _Test environment: Lab-Car (auto)

## STC-BDY02-1481

## R2065
- _Object type: Nominal Test

## R2066
- _Status: REVIEWED

## R2067: Brake light activation

## R2068
To confirm brake lights activation when NgLongitudinal in Fault

## R2069
- _Procedure: 1.Set NIgnitionStatus == PT Wake || Ignition || Powertrain Activation
  2.Set NgLongitudinal_Q != Valid

## R2070
- _Pass criteria: NBrakeLightLStatus = Active
  NBrakeLightRStatus = Active
  NBrakeLightMiddleStatus = Active

## R2071
- _Regression: No

## R2072
- _Time [hr]: 0.1

## R2073
- _Test environment: Lab-Car (auto)

## STC-BDY02-415

## R2075
- _Object type: Nominal Test

## R2076
- _Status: REVIEWED

## R2077: Brake light function activation

## R2078
Brake lights shall illuminate when deceleration rate is above 0.9 m/s2

## R2079
- _Procedure: 1.NIgntionState>=4
  2.Decelerate vehicle at the rate of change of wheel speed(nWheelFL,
  nWheelFR) is above 1.2 m/s2

## R2080
- _Pass criteria: Brake lights shall be illuminated as long as the deceleration rate is above 0.9 m/s2.
  NBrakeLightLStatus =0x1
  NBrakeLightRStatus = 0x1
  NBrakeLightMiddleStatus =0x1

## R2081
- _Regression: No

## R2082
- _Time [hr]: 0.1

## R2083
- _Test environment: Lab-Car (auto)

## STC-BDY02-419

## R2085
- _Object type: Nominal Test

## R2086
- _Status: REVIEWED

## R2087: Brake light function activation

## R2088
Brake lights shall illuminate when deceleration rate is 1.0m/s2

## R2089
- _Procedure: 1.NIgntionState>=4
  2.Decelerate vehicle at the rate of change of wheel speed(nWheelFL,
  nWheelFR) is equal to 1.0m/s2

## R2090
- _Pass criteria: Brake lights shall be illuminated as long as the deceleration rate is above 0.9 m/s2.
  NBrakeLightLStatus =0x1
  NBrakeLightRStatus = 0x1
  NBrakeLightMiddleStatus =0x1

## R2091
- _Regression: No

## R2092
- _Time [hr]: 0.1

## R2093
- _Test environment: Lab-Car (auto)

## STC-BDY02-1482

## R2095
- _Object type: Nominal Test

## R2096
- _Status: REVIEWED

## R2097: Brake light function deactivation

## R2098
To confirm brake lights deactivation when brake is released

## R2099
- _Procedure: 1.Set NIgnitionStatus == PT Wake || Ignition || Powertrain Activation
  2.NBrakepedalStatus_Q == Valid && NBrakepedalStatus != Pressed

## R2100
- _Pass criteria: NBrakeLightLStatus = Inactive
  NBrakeLightRStatus = Inactive
  NBrakeLightMiddleStatus = Inactive

## R2101
- _Regression: No

## R2102
- _Time [hr]: 0.1

## R2103
- _Test environment: Lab-Car (auto)

## STC-BDY02-1483

## R2105
- _Object type: Nominal Test

## R2106
- _Status: REVIEWED

## R2107: Brake light function deactivation

## R2108
To confirm brake lights deactivation when ESP not requested the brake light

## R2109
- _Procedure: 1.Set NIgnitionStatus == PT Wake || Ignition || Powertrain Activation
  2.NDynBrkActive == Inactive &&
  NRWUActive == Inactive

## R2110
- _Pass criteria: NBrakeLightLStatus = Inactive
  NBrakeLightRStatus = Inactive
  NBrakeLightMiddleStatus = Inactive

## R2111
- _Regression: No

## R2112
- _Time [hr]: 0.1

## R2113
- _Test environment: Lab-Car (auto)

## STC-BDY02-1484

## R2115
- _Object type: Nominal Test

## R2116
- _Status: REVIEWED

## R2117: Brake light function deactivation

## R2118
To confirm brake lights deactivation when brake is released

## R2119
- _Procedure: 1.Set NIgnitionStatus == PT Wake || Ignition || Powertrain Activation
  2.NBrakepedalStatus_Q != Valid && NpBrake_Q == Valid && pBrake < pBrakeThresholdInactive

## R2120
- _Pass criteria: NBrakeLightLStatus = Inactive
  NBrakeLightRStatus = Inactive
  NBrakeLightMiddleStatus = Inactive

## R2121
- _Regression: No

## R2122
- _Time [hr]: 0.1

## R2123
- _Test environment: Lab-Car (auto)

## STC-BDY02-1485

## R2125
- _Object type: Nominal Test

## R2126
- _Status: REVIEWED

## R2127: Brake light function deactivation

## R2128
To confirm brake lights deactivation when gLong < gLongDeactiveThreshold

## R2129
- _Procedure: 1.Set NIgnitionStatus == PT Wake || Ignition || Powertrain Activation
  2.NBrakeLightRequest == Inactive && NgLongitudinal_Q == Valid && gLong < gLongDeactiveThreshold (0.9m/s2)

## R2130
- _Pass criteria: NBrakeLightLStatus = Inactive
  NBrakeLightRStatus = Inactive
  NBrakeLightMiddleStatus = Inactive

## R2131
- _Regression: No

## R2132
- _Time [hr]: 0.1

## R2133
- _Test environment: Lab-Car (auto)

## STC-BDY02-420

## R2135
- _Object type: Nominal Test

## R2136
- _Status: REVIEWED

## R2137: Brake light function inactive

## R2138
Brake lights shall illuminate when deceleration rate is 0.9m/s2

## R2139
- _Procedure: 1.NIgntionState>=4
  2.Decelerate vehicle at the rate of change of wheel speed(nWheelFL,
  nWheelFR) is equal to 0.9m/s2

## R2140
- _Pass criteria: Brake lights shall be inactive as long as the deceleration rate is <=0.9 m/s2.
  NBrakeLightLStatus =0x0
  NBrakeLightRStatus = 0x0
  NBrakeLightMiddleStatus =0x0

## R2141
- _Regression: No

## R2142
- _Time [hr]: 0.1

## R2143
- _Test environment: Lab-Car (auto)

## STC-BDY02-1152

## R2145
- _Object type: Nominal Test

## R2146
- _Status: REVIEWED

## R2147: CHMS illumination with Brake light activation

## R2148
To confirm CHMS illumination with brake lights activation

## R2149
- _Procedure: Activate brake lights, NBrakeLightLStatus == Active
  NBrakeLightRStatus == Active
  NBrakeLightMiddleStatus == Active

## R2150
- _Pass criteria: NRHTailLampActivate_Req = Active
  NLHTailLampActivate_Req = Active
  BCHMS_LampActivateReq = Active

## R2151
- _Regression: No

## R2152
- _Time [hr]: 0.1

## R2153
- _Test environment: Lab-Car (auto)

## STC-BDY02-1153

## R2155
- _Object type: Nominal Test

## R2156
- _Status: REVIEWED

## R2157: Brake light activation with 100% PWM

## R2158
To confirm brake lights activation with 100% PWM

## R2159
- _Procedure: Activate brake lights, NBrakeLightLStatus == Active
  NBrakeLightRStatus == Active
  NBrakeLightMiddleStatus == Active

## R2160
- _Pass criteria: NRHTailLampActivate_Req = Active
  NLHTailLampActivate_Req = Active
  BCHMS_LampActivateReq = Active
  NTailInboardLampIntensity_Req 100%NTailOutboardLampIntensity_Req = 100%

## R2161
- _Regression: No

## R2162
- _Time [hr]: 0.1

## R2163
- _Test environment: Lab-Car (auto)

## STC-BDY02-1159

## R2165
- _Object type: Nominal Test

## R2166
- _Status: REVIEWED

## R2167: CHMS Short circuit fault

## R2168
To confirm CHMS lights diagnostic strategy when short circuit fault occurs

## R2169
- _Procedure: 1.Creat CHMS circuit fault i.e., short circuit fault , NCHMS_LampActiveStatus = Fault
  2.After fault, make sure the drive feedback curent is out of normal operation thresholds

## R2170
- _Pass criteria: NCHMS_LampActiveStatus = Inactive
  2.A DTC shall be raised
  3.NCHMSLightClusterMessage = Fault

## R2171
- _Regression: No

## R2172
- _Time [hr]: 0.1

## R2173
- _Test environment: Lab-Car (auto)

## STC-BDY02-1160

## R2175
- _Object type: Nominal Test

## R2176
- _Status: REVIEWED

## R2177: CHMS open circuit fault

## R2178
To confirm CHMS lights diagnostic strategy when open circuit fault occurs

## R2179
- _Procedure: 1.Creat CHMS circuit fault i.e., open circuit fault , NCHMS_LampActiveStatus = Fault
  2.After fault, make sure the drive feedback curent is out of normal operation thresholds

## R2180
- _Pass criteria: NCHMS_LampActiveStatus = Inactive
  2.A DTC shall be raised
  3.NCHMSLightClusterMessage = Fault

## R2181
- _Regression: No

## R2182
- _Time [hr]: 0.1

## R2183
- _Test environment: Lab-Car (auto)

## STC-BDY02-1161

## R2185
- _Object type: Nominal Test

## R2186
- _Status: REVIEWED

## R2187: CHMS circuit circuit fault reset

## R2188
To confirm CHMS lights fault reset with new ignition cycle

## R2189
- _Procedure: 1.Creat CHMS circuit fault i.e., Open circuit fault, NCHMS_LampActiveStatus = Fault
  2.After fault, make sure the drive feedback curent is out of normal operation thresholds
  3.Start new ignition cycle

## R2190
- _Pass criteria: NCHMS_LampActiveStatus = Inactive

## R2191
- _Regression: No

## R2192
- _Time [hr]: 0.1

## R2193
- _Test environment: Lab-Car (auto)

## STC-BDY02-411

## R2195
- _Object type: Cross Functional Test

## R2196
- _Status: REVIEWED

## R2197: Hazard light function activation (ID:STC-ADA02-04-257)

## R2198
Hazard function activation with hazard switch

## R2199
- _Procedure: 1.Set NIgnitionStatus >=0
  2.Press hazard switch, NHazardStatus =HAZARD_REQUEST

## R2200
- _Pass criteria: Haazard light function shall be activated.
  NIndicatorLOn = Active &&
  NIndicatorROn = Active &&
  NRepeaterLeftOn= Active&&
  NRepeaterRightOn= Active&&
  HazardLightButtonIlumination= ON

## R2201
- _Regression: Yes

## R2202
- _Time [hr]: 0.2

## R2203
- _Test environment: Lab-Car (auto)

## STC-BDY02-412

## R2205
- _Object type: Nominal Test

## R2206
- _Status: REVIEWED

## R2207: Hazard light function deactivation

## R2208
Hazard function deactivation with hazard switch

## R2209
- _Procedure: 1.Activate hazard light function:
  Set NIgnitionStatus>=0 && NHazardStatus =HAZARD_REQUEST
  2.Again press hazard switch,NHazardStatus =HAZARD_REQUEST

## R2210
- _Pass criteria: Haazard light function shall be deactivated.
  NIndicatorLOn = InActive &&
  NIndicatorROn = InActive &&
  NRepeaterLeftOn= InActive&&
  NRepeaterRightOn= InActive&&
  HazardLightButtonIlumination= OFF

## R2211
- _Regression: Yes

## R2212
- _Time [hr]: 0.2

## R2213
- _Test environment: Lab-Car (auto)

## STC-BDY02-409

## R2215
- _Object type: Nominal Test

## R2216
- _Status: REVIEWED

## R2217: Hazard light function activated when crash is detected

## R2218
Hazard function activation when crash is detected

## R2219
- _Procedure: 1.Set NIgnitionStatus >=0
  2.Set BCrashDetectHazardsON == Enabled && NCrashSeverity == Low Severity || High Severity
  3. Check NHazardStatus

## R2220
- _Pass criteria: NHazardStatus = Active

## R2221
- _Regression: Yes

## R2222
- _Time [hr]: 0.2

## R2223
- _Test environment: Lab-Car (auto)

## STC-BDY02-1162

## R2225
- _Object type: Nominal Test

## R2226
- _Status: REVIEWED

## R2227: Hazard light function deactivation when crash is detected

## R2228
Hazard function deactivation when crash is detected

## R2229
- _Procedure: 1.Set NIgnitionStatus >=0
  2.Enable crash detection,
  CrashDetectHazardsON =1
  3.Press Hazard switch, NHazardSwitchPressStatus == Pressed

## R2230
- _Pass criteria: NHazardStatus = Inactive

## R2231
- _Regression: Yes

## R2232
- _Time [hr]: 0.2

## R2233
- _Test environment: Lab-Car (auto)

## STC-BDY02-1168

## R2235
- _Object type: Cross Functional Test

## R2236
- _Status: REVIEWED

## R2237: Emergency braking function activated

## R2238
Emergency braking function activated when deceleration >= 6 m/s2 and vehicle speed >= 50 kph

## R2239
- _Procedure:
  1. Set NIgnitionStatus >= 5
  2. Set Vehicle deceleration >= 6 m/s2 && vehicle speed >= 50 kph

## R2240
- _Pass criteria: To verify that EmergencyBrakeIndication == ON

## R2241
- _Regression: No

## R2242
- _Time [hr]: 0.2

## R2243
- _Test environment: Lab-Car (auto)

## STC-BDY02-1169

## R2245
- _Object type: Nominal Test

## R2246
- _Status: REVIEWED

## R2247: Rear lamp stop and CHMS flash at 4 Hz

## R2248
Rear lamp stop and CHMS flash at 4 Hz when the emergency braking function is active

## R2249
- _Procedure: Set NIgnitionStatus >= 5 && EmergencyBrakeIndication == ON

## R2250
- _Pass criteria: To verify that Brake light && Central High Mounted Stop Lamp (CHMSL) flash at 4 Hz

## R2251
- _Regression: No

## R2252
- _Time [hr]: 0.2

## R2253
- _Test environment: Lab-Car (auto)

## STC-BDY02-1636

## R2255
- _Object type: Nominal Test

## R2256
- _Status: REVIEWED

## R2257: Emergency braking switching off (deceleration)

## R2258
If the emergency braking is active and the vehicle deceleration drops to <= 3.0 m/s2, the emergency braking should switch off

## R2259
- _Procedure: 1.EmergencyBrakeIndication == ON
  2.Vehicle deceleration <= 3 m/s2

## R2260
- _Pass criteria: 2. EmergencyBrakeIndication == OFF

## R2261
- _Regression: No

## R2262
- _Time [hr]: 0.2

## R2263
- _Test environment: Lab-Car (manual)

## STC-BDY02-1637

## R2265
- _Object type: Nominal Test

## R2266
- _Status: REVIEWED

## R2267: Emergency braking recovery

## R2268
If the vehicle speed at the moment the emergency braking is deactivated s >=30 kph, normal lighting logic/behaviours applies

## R2269
- _Procedure: 1.EmergencyBrakeIndication == ON
  2.Vehicle deceleration <= 3 m/s2
  3. vehicle speed >= 30 kph

## R2270
- _Pass criteria: 3.vehicle speed >= 30 kph

## R2271
- _Regression: No

## R2272
- _Time [hr]: 0.2

## R2273
- _Test environment: Lab-Car (manual)

## STC-BDY02-1170

## R2275
- _Object type: Cross Functional Test

## R2276
- _Status: REVIEWED

## R2277: Hazard light deactivation in emergency braking when BEmergencyBrakeIndication == OFF (ID:STC-CFG02-01-1170)

## R2278
To confirm Hazard light deactivation in emergency braking when BEmergencyBrakeIndication == OFF

## R2279
- _Procedure: 1.Set NIgnitionStatus >=2
  2.Disbale Emergency hazard function is turned to ON via User Preference in ICU, BEmergencyBrakeIndication == OFF
  3.Give brake pressure greater than threshold, pBrake >PEmergencyBrake

## R2280
- _Pass criteria: NHazardStatus = Inactive

## R2281
- _Regression: No

## R2282
- _Time [hr]: 0.2

## R2283
- _Test environment: Lab-Car (auto)

## STC-BDY02-1486

## R2285
- _Object type: Nominal Test

## R2286
- _Status: REVIEWED

## R2287: Hazard and panic alarm mode activation

## R2288
To confirm Hazard and panic alarm mode activation when high voltage warning is activated

## R2289
- _Procedure: 1.Set NIgnitionStatus >=2
  2.Activate high voltage warning by Hybrid system with debouncing,
  BHybridHVWarnRequest == ON
  3.Press Hazard switch

## R2290
- _Pass criteria: 2.NHazardStatus = Active
  NPanicModeActivated = Active
  DTC raised
  3.NHazardStatus == Inactive
  NPanicModeActivated == Inactive

## R2291
- _Regression: No

## R2292
- _Time [hr]: 0.1

## R2293
- _Test environment: Lab-Car (auto)

## STC-BDY02-1487

## R2295
- _Object type: Nominal Test

## R2296
- _Status: REVIEWED

## R2297: Hazard and panic alarm mode deactivation

## R2298
To confirm Hazard and panic alarm mode deactivation when high voltage warning is deactivated

## R2299
- _Procedure: 1.Set NIgnitionStatus >=2
  2.Activate high voltage warning by Hybrid system with debouncing,
  BHybridHVWarnRequest == ON
  3.High voltage warning is dismissed

## R2300
- _Pass criteria: NHazardStatus == Inactive
  NPanicModeActivated == Inactive

## R2301
- _Regression: No

## R2302
- _Time [hr]: 0.1

## R2303
- _Test environment: Lab-Car (auto)

## STC-BDY02-1172

## R2305
- _Object type: Nominal Test

## R2306
- _Status: REVIEWED

## R2307: Hazard switch button illumination and flashing during Hazard light activation

## R2308
To confirm Hazard switch button illumination and flashing during Hazard light activation

## R2309
- _Procedure: 1.Set NIgnitionStatus >=2
  2.Enable Hazard with Emergency braking, NHazardStatus = active(pBrake >PEmergencyBrake && BEmergencyBrakeIndication == OFF)

## R2310
- _Pass criteria: Hazard switch button shall be illuminated and flashing at 1.5 Hz frequency

## R2311
- _Regression: No

## R2312
- _Time [hr]: 0.2

## R2313
- _Test environment: Lab-Car (auto)

## STC-BDY02-1171

## R2315
- _Object type: Nominal Test

## R2316
- _Status: REVIEWED

## R2317: Exterior lights flash frequency and Duty cycle during Hazard light activation

## R2318
To confirm Exterior lights flash frequency and Duty cycle during Hazard light activation

## R2319
- _Procedure: 1.Set NIgnitionStatus >=2
  2.Enable Hazard with Emergency braking, NHazardStatus = active(pBrake >PEmergencyBrake && BEmergencyBrakeIndication == OFF)

## R2320
- _Pass criteria: All exterior lights shall flash at 1.5Hz frequency with 50% duty cycle, NIndicatorLOn = Flash
  NIndicatorROn = Flash
  NRepeaterLeftOn = Flash
  NRepeaterRightOn = Flash
  NRHTailLampActivate_Req = Flash
  NLHTailLampActivate_Req = Flash
  HazardLightButtonIlumination= Flash
  Tell-tales displayed in flash
  Audible warning sounded

## R2321
- _Regression: No

## R2322
- _Time [hr]: 0.2

## R2323
- _Test environment: Lab-Car (auto)

## STC-BDY02-1174

## R2325
- _Object type: Nominal Test

## R2326
- _Status: REVIEWED

## R2327: Exterior lights flash frequency and Duty cycle during Hazard light activation in ignition state <2

## R2328
To confirm Exterior lights flash frequency and Duty cycle during Hazard light activation in ignition state <2

## R2329
- _Procedure: 1.Set NIgnitionStatus < 2
  2.Enable Hazard with Emergency braking, NHazardStatus = active(pBrake >PEmergencyBrake && BEmergencyBrakeIndication == OFF)

## R2330
- _Pass criteria: Flashing at the same frequency:
  NIndicatorLOn = Flash
  NIndicatorROn = Flash
  NRepeaterLeftOn = Flash
  NRepeaterRightOn = Flash
  NRHTailLampActivate_Req = Flash
  NLHTailLampActivate_Req = Flash
  HazardLightButtonIlumination= Flash

## R2331
- _Regression: No

## R2332
- _Time [hr]: 0.2

## R2333
- _Test environment: Lab-Car (auto)

## STC-BDY02-1165

## R2335
- _Object type: Nominal Test

## R2336
- _Status: REVIEWED

## R2337: Hazard light Short circuit fault

## R2338
To confirm Hazard lights diagnostic strategy when short circuit fault occurs

## R2339
- _Procedure: 1.Creat Hazard light circuit fault i.e., short circuit fault
  2.After fault, make sure the drive feedback curent is out of normal operation thresholds

## R2340
- _Pass criteria: NHazardSwitchPressStatus = Unpressed
  2.A DTC shall be raised
  3.NHazardCtrlClusterMessage = Fault

## R2341
- _Regression: No

## R2342
- _Time [hr]: 0.1

## R2343
- _Test environment: Lab-Car (auto)

## STC-BDY02-1166

## R2345
- _Object type: Nominal Test

## R2346
- _Status: REVIEWED

## R2347: Hazard light open circuit fault

## R2348
To confirm Hazard lights diagnostic strategy when open circuit fault occurs

## R2349
- _Procedure: 1.Creat Hazard light circuit fault i.e., open circuit fault
  2.After fault, make sure the drive feedback curent is out of normal operation thresholds

## R2350
- _Pass criteria: NHazardSwitchPressStatus = Unpressed
  2.A DTC shall be raised
  3.NHazardCtrlClusterMessage = Fault

## R2351
- _Regression: No

## R2352
- _Time [hr]: 0.1

## R2353
- _Test environment: Lab-Car (auto)

## STC-BDY02-1167

## R2355
- _Object type: Nominal Test

## R2356
- _Status: REVIEWED

## R2357: Hazard light circuit circuit fault reset

## R2358
To confirm Hazard lights fault reset with new ignition cycle

## R2359
- _Procedure: 1.Creat Hazard light circuit fault i.e., Open circuit fault
  HSD11_2 = Open circuit or short to Gnd
  2.After fault, make sure the drive feedback curent is out of normal operation thresholds
  3.Start new ignition cycle

## R2360
- _Pass criteria: NHazardSwitchPressStatus = Unpressed

## R2361
- _Regression: No

## R2362
- _Time [hr]: 0.1

## R2363
- _Test environment: Lab-Car (auto)

## STC-BDY02-1638

## R2365
- _Object type: Nominal Test

## R2366
- _Status: REVIEWED

## R2367: Hazard Light Button DTC

## R2368
The hazard button illumination shall be driven by a PWM HSD by the domain controller, so if a fault is detected a DTC shall be raised.

## R2369
- _Procedure: 1.Creat Hazard light circuit fault i.e., Open circuit fault
  HSD11_2 = Open circuit or short to Gnd
  2. Press the hazard button

## R2370
- _Pass criteria: 2. DTC raised

## R2371
- _Regression: No

## R2372
- _Time [hr]: 0.2

## R2373
- _Test environment: Lab-Car (manual)

## STC-BDY02-1175

## R2375
- _Object type: Nominal Test

## R2376
- _Status: REVIEWED

## R2377: Right Directional Indicator Activation

## R2378
To confirm Right Directional Indicator Activation when DIMS stalk is pushed Upwards

## R2379
- _Procedure: 1.Set NIgnitionStatus == (Ignition || Powertrain Activation)
  2.Puh DIMS stalk Upwards, NDISwitch == Upwards

## R2380
- _Pass criteria: NIndicatorRStatus = Active

## R2381
- _Regression: No

## R2382
- _Time [hr]: 0.1

## R2383
- _Test environment: Lab-Car (auto)

## STC-BDY02-1176

## R2385
- _Object type: Nominal Test

## R2386
- _Status: REVIEWED

## R2387: Left Directional Indicator Activation

## R2388
To confirm Left Directional Indicator Activation when DIMS stalk is pushed Downwards

## R2389
- _Procedure: 1.Set NIgnitionStatus == (Ignition || Powertrain Activation)
  2.Puh DIMS stalk Downwards, NDISwitch == Downwards

## R2390
- _Pass criteria: NIndicatorLStatus = Active

## R2391
- _Regression: No

## R2392
- _Time [hr]: 0.1

## R2393
- _Test environment: Lab-Car (auto)

## STC-BDY02-1177

## R2395
- _Object type: Nominal Test

## R2396
- _Status: REVIEWED

## R2397: Exterior lamps illumination when Right Directional Indicator is Activated

## R2398
To confirm Exterior lamps illumination when Right Directional Indicator is Activated

## R2399
- _Procedure: 1.Set NIgnitionStatus == (Ignition || Powertrain Activation)
  2.Puh DIMS stalk Upwards, NDISwitch == Upwards

## R2400
- _Pass criteria: NInidcatorROn = Active
  NRepeaterRightOn = Active
  NTailLightRightStatus = Active

## R2401
- _Regression: No

## R2402
- _Time [hr]: 0.1

## R2403
- _Test environment: Lab-Car (auto)

## STC-BDY02-1178

## R2405
- _Object type: Nominal Test

## R2406
- _Status: REVIEWED

## R2407: Exterior lamps illumination when Left Directional Indicator is Activated

## R2408
To confirm Exterior lamps illumination when Left Directional Indicator is Activated

## R2409
- _Procedure: 1.Set NIgnitionStatus == (Ignition || Powertrain Activation)
  2.Puh DIMS stalk Downwards, NDISwitch == Downwards

## R2410
- _Pass criteria: NInidcatorLOn = Active
  NRepeaterLeftOn = Active
  NTailLightLeftStatus = Active

## R2411
- _Regression: No

## R2412
- _Time [hr]: 0.1

## R2413
- _Test environment: Lab-Car (auto)

## STC-BDY02-1179

## R2415
- _Object type: Nominal Test

## R2416
- _Status: REVIEWED

## R2417: DI flash frequency with 50%

## R2418
To confirm DI flash frequency

## R2419
- _Procedure: NIndicatorRStatus == Active ||
  NIndicatorLStatus == Active

## R2420
- _Pass criteria: All related DI lamps flash at 1.5Hz with 50% duty cycle

## R2421
- _Regression: No

## R2422
- _Time [hr]: 0.1

## R2423
- _Test environment: Lab-Car (auto)

## STC-BDY02-1180

## R2425
- _Object type: Nominal Test

## R2426
- _Status: REVIEWED

## R2427: Directional Indicator function deactivation with Hazard activation

## R2428
To confirm DI function deactivation when hazard function is activated

## R2429
- _Procedure: 1.Activate Directional Indicator function, NIndicatorRStatus == Active ||
  NIndicatorLStatus == Active
  2.Press Hazard button, NHazardStatus == Active

## R2430
- _Pass criteria: NIndicatorRStatus = Inactive
  NIndicatorLStatus = Inactive
  after the last flash

## R2431
- _Regression: No

## R2432
- _Time [hr]: 0.1

## R2433
- _Test environment: Lab-Car (auto)

## STC-BDY02-1181

## R2435
- _Object type: Nominal Test

## R2436
- _Status: REVIEWED

## R2437: Tell tale display when Directional Indicator function activated

## R2438
To confirm Tell tale display when Directional Indicator function activated

## R2439
- _Procedure: 1.Activate Directional Indicator function, NIndicatorRStatus == Active ||
  NIndicatorLStatus == Active

## R2440
- _Pass criteria: Direction Indicator function status for the telltale, to indicate a green arrow consistent with the user direction request and an audible warning flash at 1.5 Hz frequency, synchronised with the direction indicator lights

## R2441
- _Regression: No

## R2442
- _Time [hr]: 0.1

## R2443
- _Test environment: Lab-Car (manual)

## STC-BDY02-399

## R2445
- _Object type: Nominal Test

## R2446
- _Status: REVIEWED

## R2447: Left Direction indicator no of flashes

## R2448
Left Direction indicator lights no of flashes equals to DILaneChangeFlashes

## R2449
- _Procedure: 1.Set NIgnitionStatus>=5
  2.Turn DIMS stalk left for less than DIMomentaryRequestTime i.e., 2sec(NDISwitch = 1 for <2sec)

## R2450
- _Pass criteria: DILeftState_Active && Left Direction indicator light number of flashes equal to DILaneChangeFlashes i.e.,3 flashes,
  NInidcatorLOn = Active &&
  NRepeaterLeftOn= Active

## R2451
- _Regression: Yes

## R2452
- _Time [hr]: 0.1

## R2453
- _Test environment: Lab-Car (auto)

## STC-BDY02-404

## R2455
- _Object type: Nominal Test

## R2456
- _Status: REVIEWED

## R2457: Right Direction indicator no of flashes

## R2458
Right Direction indicator lights no of flashes equals to DILaneChangeFlashes

## R2459
- _Procedure: 1.Set NIgnitionStatus>=5
  2.Turn DIMS stalk right for less than DIMomentaryRequestTime i.e., 2sec(NDISwitch = 3 for <2sec)

## R2460
- _Pass criteria: DIRighttState_Active && Right Direction indicator light number of flashes equal to DILaneChangeFlashes i.e.,3 flashes,
  NInidcatorROn = Active &&
  NRepeaterRightOn= Active

## R2461
- _Regression: Yes

## R2462
- _Time [hr]: 0.1

## R2463
- _Test environment: Lab-Car (auto)

## STC-BDY02-405

## R2465
- _Object type: Nominal Test

## R2466
- _Status: REVIEWED

## R2467: Left Direction indicator no of flashes

## R2468
Left Direction indicator lights no of flashes equals to DIMS stalk activation time

## R2469
- _Procedure: 1.Set NIgnitionStatus>=5
  2.Turn DIMS stalk left for longer than DIMomentaryRequestTime i.e., 2sec(NDISwitch = 1 for >2sec)

## R2470
- _Pass criteria: DILeftState_Active && Left Direction indicator light shall flash for the duration DIMS stalk is activated,
  NInidcatorLOn = Active &&
  NRepeaterLeftOn= Active

## R2471
- _Regression: Yes

## R2472
- _Time [hr]: 0.1

## R2473
- _Test environment: Lab-Car (auto)

## STC-BDY02-406

## R2475
- _Object type: Nominal Test

## R2476
- _Status: REVIEWED

## R2477: Right Direction indicator no of flashes

## R2478
Right Direction indicator lights no of flashes equals to DIMS stalk activation time

## R2479
- _Procedure: 1.Set NIgnitionStatus>=5
  2.Turn DIMS stalk right for longer than DIMomentaryRequestTime i.e., 2sec(NDISwitch = 3 for >2sec)

## R2480
- _Pass criteria: DIRighttState_Active && Right Direction indicator light shall flash for the duration DIMS stalk is activated,
  NInidcatorROn = Active &&
  NRepeaterRightOn= Active

## R2481
- _Regression: Yes

## R2482
- _Time [hr]: 0.1

## R2483
- _Test environment: Lab-Car (auto)

## STC-BDY02-400

## R2485
- _Object type: Nominal Test

## R2486
- _Status: REVIEWED

## R2487: DIMS input received for opposite direction

## R2488
Directional indicator function when DIMS input received for opposite direction

## R2489
- _Procedure: 1.Enable Left direction indicator light:
  Set NIgnitionStatus>=5 && NDISwitch = 1
  2.Turn DIMS stalk Right (NDISwitch = 3) immediately within no time

## R2490
- _Pass criteria: Direction indicator function shall be Inactive for PostLaneChangeCancellationDelay i.e.,500ms,
  DIState_Inactive && NInidcatorLOn = InActive && NRepeaterLeftOn= InActive.
  After 500ms,Right direction indicator light shall be active,NInidcatorROn = Active &&
  NRepeaterRightOn= Active,
  NInidcatorLOn = InActive &&
  NRepeaterLeftOn= InActive

## R2491
- _Regression: Yes

## R2492
- _Time [hr]: 0.1

## R2493
- _Test environment: Lab-Car (auto)

## STC-BDY02-407

## R2495
- _Object type: Nominal Test

## R2496
- _Status: REVIEWED

## R2497: DIMS input received for opposite direction

## R2498
Directional indicator function when DIMS input received for opposite direction

## R2499
- _Procedure: 1.Enable Right direction indicator light:
  Set NIgnitionStatus >=5 && NDISwitch = 3
  2.Turn DIMS stalk Left(NDISwitch = 1) immediately within no time

## R2500
- _Pass criteria: Direction indicator function shall be Inactive for PostLaneChangeCancellationDelay i.e.,500ms,
  DIState_Inactive && NInidcatorROn = InActive && NRepeaterRightOn= InActive.
  After 500ms,Left direction indicator light shall be active,NInidcatorLOn = Active &&
  NRepeaterLeftOn= Active,
  NInidcatorROn = InActive &&
  NRepeaterRightOn= InActive

## R2501
- _Regression: Yes

## R2502
- _Time [hr]: 0.1

## R2503
- _Test environment: Lab-Car (auto)

## STC-BDY02-1185

## R2505
- _Object type: Nominal Test

## R2506
- _Status: REVIEWED

## R2507: Direction indicator lamps Short circuit fault

## R2508
To confirm Direction indicator lamps diagnostic strategy when short circuit fault occurs

## R2509
- _Procedure: 1.Creat Direction indicator lamps circuit fault i.e., short circuit fault
  2.After fault, make sure the drive feedback curent is out of normal operation thresholds

## R2510
- _Pass criteria: NFrontIndicatorLONActiveSts = Fault
  NFrontIndicatorRONActiveSts = Fault
  NLHSideRepeaterONSts = Fault
  NRHSideRepeaterONSts = Fault
  NHazardSwitchPressStatus = Unpressed
  2.A DTC shall be raised
  3.NHazardCtrlClusterMessage = Fault

## R2511
- _Regression: No

## R2512
- _Time [hr]: 0.1

## R2513
- _Test environment: Lab-Car (auto)

## STC-BDY02-1186

## R2515
- _Object type: Nominal Test

## R2516
- _Status: REVIEWED

## R2517: Direction indicator lampsopen circuit fault

## R2518
To confirm Direction indicator lamps diagnostic strategy when open circuit fault occurs

## R2519
- _Procedure: 1.Creat Direction indicator lamps circuit fault i.e., open circuit fault
  2.After fault, make sure the drive feedback curent is out of normal operation thresholds

## R2520
- _Pass criteria: NFrontIndicatorLONActiveSts = Fault
  NFrontIndicatorRONActiveSts = Fault
  NLHSideRepeaterONSts = Fault
  NRHSideRepeaterONSts = Fault
  NHazardSwitchPressStatus = Unpressed
  2.A DTC shall be raised
  3.NHazardCtrlClusterMessage = Fault

## R2521
- _Regression: No

## R2522
- _Time [hr]: 0.1

## R2523
- _Test environment: Lab-Car (auto)

## STC-BDY02-1187

## R2525
- _Object type: Nominal Test

## R2526
- _Status: REVIEWED

## R2527: Direction indicator lamps circuit circuit fault reset

## R2528
To confirm Direction indicator lamps fault reset with new ignition cycle

## R2529
- _Procedure: 1.Creat Direction indicator lamps circuit fault i.e., Open circuit fault
  2.After fault, make sure the drive feedback curent is out of normal operation thresholds
  3.Start new ignition cycle

## R2530
- _Pass criteria: LeftIndicatorFault,
  RightIndicatorFault,
  LeftRepeaterFault,
  RightRepeaterFault

## R2531
- _Regression: No

## R2532
- _Time [hr]: 0.1

## R2533
- _Test environment: Lab-Car (auto)

## STC-BDY02-1317

## R2535
- _Object type: Nominal Test

## R2536
- _Status: REVIEWED

## R2537: Alarm status indication

## R2538
To confirm Alarm status indication

## R2539
- _Procedure: 1.Set igniton state = any value
  2.NAlarmStatus == Triggered

## R2540
- _Pass criteria: All the DIs shall Flash at a calibratable frequency AlarmIndicationActive (1.5Hz) and at a duty cycle calibrated AlarmTriggerDuty (50%)

## R2541
- _Regression: No

## R2542
- _Time [hr]: 0.2

## R2543
- _Test environment: Lab-Car (manual)

## STC-BDY02-352

## R2545
- _Object type: Nominal Test

## R2546
- _Status: REVIEWED

## R2547: Fog light activation

## R2548
Fog light activation

## R2549
- _Procedure: 1.Set ignition status = 5||6
  2.Set MasterLightSwitch = A||2 and press centre button on the Master Light switch

## R2550
- _Pass criteria: FogLightAvailable = True & Fog light shall illuminate

## R2551
- _Regression: Yes

## R2552
- _Time [hr]: 0.1

## R2553
- _Test environment: Lab-Car (auto)

## STC-BDY02-356

## R2555
- _Object type: Nominal Test

## R2556
- _Status: REVIEWED

## R2557: Fog light NOT available

## R2558
Fog light NOT available when ignition state<5

## R2559
- _Procedure: 1.Set ignition status < 5
  2.Set MasterLightSwitch = A||2 and press centre button on the Master Light switch

## R2560
- _Pass criteria: FogLightAvailable = False & Fog light OFF

## R2561
- _Regression: No

## R2562
- _Time [hr]: 0.1

## R2563
- _Test environment: Lab-Car (auto)

## STC-BDY02-357

## R2565
- _Object type: Nominal Test

## R2566
- _Status: REVIEWED

## R2567: Fog light NOT available

## R2568
Fog light NOT available when Master Light Switch !=A||2

## R2569
- _Procedure: 1.Set ignition status = 5||6
  2.Set MasterLightSwitch != A||2 and press centre button on the Master Light switch

## R2570
- _Pass criteria: FogLightAvailable = False & Fog light OFF

## R2571
- _Regression: No

## R2572
- _Time [hr]: 0.1

## R2573
- _Test environment: Lab-Car (auto)

## STC-BDY02-358

## R2575
- _Object type: Negative Test

## R2576
- _Status: REVIEWED

## R2577: Fog light deactivation

## R2578
Fog light deactivation by exiting current ignition state

## R2579
- _Procedure: 1.Activate Fog light(ignition status = 5||6 &&
  MasterLightSwitch = A||2)
  2.Set ignition status < 5

## R2580
- _Pass criteria: 1.FogLightAvailable = True & Fog light shall illuminate
  2.FogLightAvailable = False & Fog light OFF

## R2581
- _Regression: No

## R2582
- _Time [hr]: 0.1

## R2583
- _Test environment: Lab-Car (auto)

## STC-BDY02-359

## R2585
- _Object type: Negative Test

## R2586
- _Status: REVIEWED

## R2587: Fog light deactivation

## R2588
Fog light deactivation by master light switch

## R2589
- _Procedure: 1.Activate Fog light(ignition status = 5||6 &&
  MasterLightSwitch = A||2)
  2.Set MasterLightSwitch != A||2

## R2590
- _Pass criteria: 1.FogLightAvailable = True & Fog light shall illuminate
  2.FogLightAvailable = False & Fog light OFF

## R2591
- _Regression: No

## R2592
- _Time [hr]: 0.1

## R2593
- _Test environment: Lab-Car (auto)

## STC-BDY02-501

## R2595
- _Object type: Nominal Test

## R2596
- _Status: REVIEWED

## R2597: Rear fog light activation

## R2598
Rear fog light activation

## R2599
- _Procedure: 1.Set Ignition state>=5
  2.Rear Fog light is Inactive,
  FogLightAvailable = True && FogLightActive= False
  3.MLS =Auto||Dipped
  4.Press Fog light switch i.e., press the centre button in Master Light Switch (rising edge)

## R2600
- _Pass criteria: 4.FogLightActive= True, NFogLightRstatus= 0x1.
  Turn on the Fog Light
  Turn on the Dipped Beam.
  NFogLightRstatus =0x1
  NDippedBeamLeftStatus = (0x1)
  NDippedBeamRightStatus = (0x1)

## R2601
- _Regression: Yes

## R2602
- _Time [hr]: 0.1

## R2603
- _Test environment: Lab-Car (auto)

## STC-BDY02-511

## R2605
- _Object type: Negative Test

## R2606
- _Status: REVIEWED

## R2607: Fog light deactivation with ignition state

## R2608
Fog light deactivation when ignition state is <5

## R2609
- _Procedure: 1.Activate Rear Fog light :
  FogLightActive= True && NFogLightRstatus= 0x1
  2.Set ignition state <5

## R2610
- _Pass criteria: 1.IFogLightActive= True
  Turn ON the Fog Light
  Turn ON the Dipped Beam
  2.FogLightActive= False
  Turn Off the Fog Light
  Turn off the Dipped Beam

## R2611
- _Regression: No

## R2612
- _Time [hr]: 0.1

## R2613
- _Test environment: Lab-Car (auto)

## STC-BDY02-512

## R2615
- _Object type: Negative Test

## R2616
- _Status: REVIEWED

## R2617: Fog light deactivation with MLS

## R2618
Fog light deactivation when
MLS !=Auto|| Dipped

## R2619
- _Procedure: 1.Activate Rear Fog light :
  FogLightActive= True && NFogLightRstatus= 0x1
  2.Set MLS !=Auto||Dipped

## R2620
- _Pass criteria: 1.IFogLightActive= True
  Turn ON the Fog Light
  Turn ON the Dipped Beam
  2.FogLightActive= False
  Turn Off the Fog Light
  Turn off the Dipped Beam

## R2621
- _Regression: No

## R2622
- _Time [hr]: 0.1

## R2623
- _Test environment: Lab-Car (auto)

## STC-BDY02-508

## R2625
- _Object type: Nominal Test

## R2626
- _Status: REVIEWED

## R2627: Rear fog light deactivation

## R2628
Rear fog light deactivation

## R2629
- _Procedure: 1.Activate Rear Fog light: FogLightActive= True &&
  Fog Light Switch press(rising edge )
  2.Press Fog light switch again i.e., press the centre button in Master Light Switch (rising edge)

## R2630
- _Pass criteria: 2.FogLightActive= False
  Turn Off the Fog Light
  Turn off the Dipped Beam.
  NFogLightRstatus =0x0
  NDippedBeamLeftStatus = (0x0)
  NDippedBeamRightStatus = (0x0)

## R2631
- _Regression: Yes

## R2632
- _Time [hr]: 0.1

## R2633
- _Test environment: Lab-Car (auto)

## STC-BDY02-502

## R2635
- _Object type: Nominal Test

## R2636
- _Status: REVIEWED

## R2637: Dipped beam kept ON

## R2638
Dipped beam kept ON while MLS is in Auto position when Fog is activated

## R2639
- _Procedure: Activate Rear Fog light while the Master Light Switch is in AUTO position : FogLightActive= True &&
  Fog Light Switch press(rising edge ) && MasterLightSwitch = A

## R2640
- _Pass criteria: Dipped beam kept ON.
  NDippedBeamLeftStatus = (0x1)
  NDippedBeamRightStatus = (0x1)

## R2641
- _Regression: No

## R2642
- _Time [hr]: 0.1

## R2643
- _Test environment: Lab-Car (auto)

## STC-BDY02-503

## R2645
- _Object type: Nominal Test

## R2646
- _Status: REVIEWED

## R2647: Dipped beam with Fog light

## R2648
Dipped beam while MLS in Auto position and when Fog light is deactivated

## R2649
- _Procedure: 1.Activate Rear Fog light while the Master Light Switch is in AUTO position : FogLightActive= True &&
  Fog Light Switch press(rising edge ) && MasterLightSwitch = A
  2.Deactivate the Fog light by pressing the the centre button in Master Light Switch (rising edge)

## R2650
- _Pass criteria: 2. Dipped beam OFF

## R2651
- _Regression: No

## R2652
- _Time [hr]: 0.1

## R2653
- _Test environment: Lab-Car (auto)

## STC-BDY02-509

## R2655
- _Object type: Nominal Test

## R2656
- _Status: REVIEWED

## R2657: Dipped beam with Fog light

## R2658
Dipped beam while MLS in Side position and when Fog light is activated

## R2659
- _Procedure: 1.Activate Rear Fog light while the Master Light Switch is in AUTO position : FogLightActive= True &&
  Fog Light Switch press(rising edge ) && MasterLightSwitch = A
  2.Set Master light switch to Side position

## R2660
- _Pass criteria: 2. Dipped beam OFF

## R2661
- _Regression: No

## R2662
- _Time [hr]: 0.1

## R2663
- _Test environment: Lab-Car (auto)

## STC-BDY02-1639

## R2665
- _Object type: Nominal Test

## R2666
- _Status: REVIEWED

## R2667: Fog Light Lamp

## R2668
The fog lamp shall be illuminated when the fog light function is activated

## R2669
- _Procedure: NFogLightRStatus == Active

## R2670
- _Pass criteria: NFogLampDrvrStatus = Active

## R2671
- _Regression: No

## R2672
- _Time [hr]: 0.1

## R2673
- _Test environment: Lab-Car (manual)

## STC-BDY02-504

## R2675
- _Object type: Cross Functional Test

## R2676
- _Status: REVIEWED

## R2677: Fog light telltale (ID: STC-HMI01-236)

## R2678
Fog light telltale activation when Fog lights are active

## R2679
- _Procedure: Activate Rear Fog light :
  NFogLightRstatus= 0x1

## R2680
- _Pass criteria: Rear Fog light telltale shall be displayed on driver display

## R2681
- _Regression: Yes

## R2682
- _Time [hr]: 0.1

## R2683
- _Test environment: Lab-Car (manual)

## STC-BDY02-505

## R2685
- _Object type: Nominal Test

## R2686
- _Status: REVIEWED

## R2687: Fog light telltale inactive with default value

## R2688
Rear fog light telltale shall be inactive when fog light signals in default value for 5 times

## R2689
- _Procedure: 1.Activate Rear Fog light :
  NFogLightRstatus= 0x1
  2.Simulate Rear Fog light signal as default value(NFogLightRstatus=0x3) and send 5 consecutive times onto the bus

## R2690
- _Pass criteria: 1.Rear Fog light telltale shall be displayed on driver display
  2.Rear Fog light Telltale shall not be displayed

## R2691
- _Regression: No

## R2692
- _Time [hr]: 0.1

## R2693
- _Test environment: Lab-Car (manual)

## STC-BDY02-506

## R2695
- _Object type: Nominal Test

## R2696
- _Status: REVIEWED

## R2697: Fog light telltale inactive with CAN timeout

## R2698
Rear fog light telltale shall be inactive when CAN timeout occurs on the Rear Fog Light signal

## R2699
- _Procedure: 1.Activate Rear Fog light :
  NFogLightRstatus= 0x1
  2.Remove fog light switch in order to stop rear fog light signal for CAN timeout duration

## R2700
- _Pass criteria: 1.Rear Fog light telltale shall be displayed on driver display
  2.Rear Fog light Telltale shall not be displayed

## R2701
- _Regression: No

## R2702
- _Time [hr]: 0.1

## R2703
- _Test environment: Lab-Car (manual)

## STC-BDY02-510

## R2705
- _Object type: Nominal Test

## R2706
- _Status: REVIEWED

## R2707: Fog light switch LED illumination

## R2708
LED in Fog light switch shall be illuminate when Fog light is active

## R2709
- _Procedure: 1.Activate Rear Fog light :
  FogLightActive= True && NFogLightRstatus= 0x1
  2.Deactivate Rear Fog light:
  FogLightActive= False &&NFogLightRstatus= 0x0

## R2710
- _Pass criteria: 1.Illuminate the Fog Light Switch LED
  2.Deilluminate the Fog Light Switch LED

## R2711
- _Regression: Yes

## R2712
- _Time [hr]: 0.1

## R2713
- _Test environment: Lab-Car (auto)

## STC-BDY02-1190

## R2715
- _Object type: Nominal Test

## R2716
- _Status: REVIEWED

## R2717: Fog lamp Short circuit fault

## R2718
To confirm fog lamp diagnostic strategy when short circuit fault occurs

## R2719
- _Procedure: 1.Creat fog lamp circuit fault i.e., short circuit fault , NFogLampDrvrStatus = Fault
  2.After fault, make sure the drive feedback curent is out of normal operation thresholds

## R2720
- _Pass criteria: NFogLampDrvrStatus = Fault
  2.A DTC shall be raised
  3.NFogLightClusterMessage = Fault

## R2721
- _Regression: No

## R2722
- _Time [hr]: 0.1

## R2723
- _Test environment: Lab-Car (auto)

## STC-BDY02-1191

## R2725
- _Object type: Nominal Test

## R2726
- _Status: REVIEWED

## R2727: Fog lamp open circuit fault

## R2728
To confirm fog lamp diagnostic strategy when open circuit fault occurs

## R2729
- _Procedure: 1.Creat fog lamp circuit fault i.e., open circuit fault , NFogLampDrvrStatus = Fault
  2.After fault, make sure the drive feedback curent is out of normal operation thresholds

## R2730
- _Pass criteria: NFogLampDrvrStatus = Fault
  2.A DTC shall be raised
  3.NFogLightClusterMessage = Fault

## R2731
- _Regression: No

## R2732
- _Time [hr]: 0.1

## R2733
- _Test environment: Lab-Car (auto)

## STC-BDY02-1192

## R2735
- _Object type: Nominal Test

## R2736
- _Status: REVIEWED

## R2737: Fog lamp circuit circuit fault reset

## R2738
To confirm fog lamp fault reset with new ignition cycle

## R2739
- _Procedure: 1.Creat fog lamp circuit fault i.e., Open circuit fault, NFogLampDrvrStatus = Fault
  2.After fault, make sure the drive feedback curent is out of normal operation thresholds
  3.Start new ignition cycle

## R2740
- _Pass criteria: NFogLampDrvrStatus = Inactive

## R2741
- _Regression: No

## R2742
- _Time [hr]: 0.1

## R2743
- _Test environment: Lab-Car (auto)

## STC-BDY02-1194

## R2745
- _Object type: Nominal Test

## R2746
- _Status: REVIEWED

## R2747: License plate illumination

## R2748
To confirm license plate illumination when side || dipped beam is active

## R2749
- _Procedure: 1.Activate Side lights or Dipped beam function(Set NIgnitionStatus =2 && NMasterLightStatus == Side Light || Dipped Beam)

## R2750
- _Pass criteria: BLicenseLampActivateReq = Active && NLHLicenseLampActiveSts = Active
  NRHLicenseLampActiveSts = Active

## R2751
- _Regression: No

## R2752
- _Time [hr]: 0.1

## R2753
- _Test environment: Lab-Car (auto)

## STC-BDY02-1197

## R2755
- _Object type: Nominal Test

## R2756
- _Status: REVIEWED

## R2757: License plate illumination deactivation

## R2758
To confirm license plate illumination deactivation when side || dipped beam is inactive

## R2759
- _Procedure: 1.Activate Side lights or Dipped beam function(Set NIgnitionStatus =2 && NMasterLightStatus == Side Light || Dipped Beam)
  2.Inactivate Side lights or Dipped beam function,NMasterLightStatus !== Side Light || Dipped Beam

## R2760
- _Pass criteria: BLicenseLampActivateReq = Inactive

## R2761
- _Regression: No

## R2762
- _Time [hr]: 0.1

## R2763
- _Test environment: Lab-Car (auto)

## STC-BDY02-1200

## R2765
- _Object type: Nominal Test

## R2766
- _Status: REVIEWED

## R2767: License plate lamp Short circuit fault

## R2768
To confirm license plate lamp diagnostic strategy when short circuit fault occurs

## R2769
- _Procedure: 1.Creat license plate lamp circuit fault i.e., short circuit fault , NLHLicenseLampActiveSts = Fault
  OR
  NRHLicenseLampActiveSts = Fault
  2.After fault, make sure the drive feedback curent is out of normal operation thresholds

## R2770
- _Pass criteria: NLHLicenseLampActiveSts = Inactive
  NRHLicenseLampActiveSts = Inactive
  2.A DTC shall be raised
  3.NLicensePlateClusterMessage = Fault

## R2771
- _Regression: No

## R2772
- _Time [hr]: 0.1

## R2773
- _Test environment: Lab-Car (auto)

## STC-BDY02-1201

## R2775
- _Object type: Nominal Test

## R2776
- _Status: REVIEWED

## R2777: License plate lamp open circuit fault

## R2778
To confirm license plate lamp diagnostic strategy when open circuit fault occurs

## R2779
- _Procedure: 1.Creat license plate lamp circuit fault i.e., open circuit fault , NLHLicenseLampActiveSts = Fault
  OR
  NRHLicenseLampActiveSts = Fault
  2.After fault, make sure the drive feedback curent is out of normal operation thresholds

## R2780
- _Pass criteria: NLHLicenseLampActiveSts = Inactive
  NRHLicenseLampActiveSts = Inactive
  2.A DTC shall be raised
  3.NLicensePlateClusterMessage = Fault

## R2781
- _Regression: No

## R2782
- _Time [hr]: 0.1

## R2783
- _Test environment: Lab-Car (auto)

## STC-BDY02-1202

## R2785
- _Object type: Nominal Test

## R2786
- _Status: REVIEWED

## R2787: License plate lamp circuit circuit fault reset

## R2788
To confirm license plate lamp fault reset with new ignition cycle

## R2789
- _Procedure: 1.Creat license plate lamp circuit fault i.e., Open circuit fault, NLHLicenseLampActiveSts = Fault
  OR
  NRHLicenseLampActiveSts = Fault
  2.After fault, make sure the drive feedback curent is out of normal operation thresholds
  3.Start new ignition cycle

## R2790
- _Pass criteria: NLHLicenseLampActiveSts = Inactive
  NRHLicenseLampActiveSts = Inactive

## R2791
- _Regression: No

## R2792
- _Time [hr]: 0.1

## R2793
- _Test environment: Lab-Car (auto)

## STC-BDY02-1209

## R2795
- _Object type: Nominal Test

## R2796
- _Status: REVIEWED

## R2797: Reverse light activation

## R2798
To confirm reverse light activation when reverse gear is engaged

## R2799
- _Procedure: 1.Set NIgnitionStatus == Ignition || Activation
  2.Engage gear is in Reverse Gear, GearEngaged == Reverse Gear

## R2800
- _Pass criteria: NReverseLightStatus = Active && NReverseLampActiveStatus = Active

## R2801
- _Regression: No

## R2802
- _Time [hr]: 0.1

## R2803
- _Test environment: Lab-Car (auto)

## STC-BDY02-1210

## R2805
- _Object type: Nominal Test

## R2806
- _Status: REVIEWED

## R2807: Reverse light inactivation

## R2808
To confirm reverse light inactivation when reverse gear is not engaged

## R2809
- _Procedure: 1.Activate Reverse light, (Set NIgnitionStatus == Ignition || Activation
  && GearEngaged == Reverse Gear)
  2.GearEngaged !== Reverse Gear

## R2810
- _Pass criteria: NReverseLightStatus = inActive && NReverseLampActiveStatus = inActive

## R2811
- _Regression: No

## R2812
- _Time [hr]: 0.1

## R2813
- _Test environment: Lab-Car (auto)

## STC-BDY02-1206

## R2815
- _Object type: Nominal Test

## R2816
- _Status: REVIEWED

## R2817: Reverse Light Short circuit fault

## R2818
To confirm Reverse Light diagnostic strategy when short circuit fault occurs

## R2819
- _Procedure: 1.Creat Reverse Light circuit fault i.e., short circuit fault , NReverseLampActiveStatus = Fault
  2.After fault, make sure the drive feedback curent is out of normal operation thresholds

## R2820
- _Pass criteria: 1.NReverseLampActiveStatus = Inactive
  2.A DTC shall be raised
  3.NReverseLightClusterMessage = Fault

## R2821
- _Regression: No

## R2822
- _Time [hr]: 0.1

## R2823
- _Test environment: Lab-Car (auto)

## STC-BDY02-1207

## R2825
- _Object type: Nominal Test

## R2826
- _Status: REVIEWED

## R2827: Reverse Light open circuit fault

## R2828
To confirm Reverse Light diagnostic strategy when open circuit fault occurs

## R2829
- _Procedure: 1.Creat Reverse Light circuit fault i.e., open circuit fault , NReverseLampActiveStatus = Fault
  2.After fault, make sure the drive feedback curent is out of normal operation thresholds

## R2830
- _Pass criteria: 1.NReverseLampActiveStatus = Inactive
  2.A DTC shall be raised
  3.NReverseLightClusterMessage = Fault

## R2831
- _Regression: No

## R2832
- _Time [hr]: 0.1

## R2833
- _Test environment: Lab-Car (auto)

## STC-BDY02-1208

## R2835
- _Object type: Nominal Test

## R2836
- _Status: REVIEWED

## R2837: Reverse Light circuit circuit fault reset

## R2838
To confirm Reverse Light fault reset with new ignition cycle

## R2839
- _Procedure: 1.Creat Reverse Light circuit fault i.e., Open circuit fault, NReverseLampActiveStatus = Fault
  2.After fault, make sure the drive feedback curent is out of normal operation thresholds
  3.Start new ignition cycle

## R2840
- _Pass criteria: NReverseLampActiveStatus = Inactive

## R2841
- _Regression: No

## R2842
- _Time [hr]: 0.1

## R2843
- _Test environment: Lab-Car (auto)

## STC-BDY02-361

## R2845
- _Object type: Negative Test

## R2846
- _Status: REVIEWED

## R2847: Parking light deactivation

## R2848
Parking light deactivation when igniton state>2

## R2849
- _Procedure: 1.Enable parking light function(Ignition status = 2 && NDISwitch=3||1)
  2.Set ignition status > 2

## R2850
- _Pass criteria: 1.ParkingLightActive = True,
  Side lights, Side Marker and Tail lamps shall active when parking ligts are activated
  2.ParkingLightAvailable = False,
  Side lights, Side Marker and Tail lamps are OFF

## R2851
- _Regression: No

## R2852
- _Time [hr]: 0.1

## R2853
- _Test environment: Lab-Car (auto)

## STC-BDY02-366

## R2855
- _Object type: Negative Test

## R2856
- _Status: REVIEWED

## R2857: Parking light deactivation

## R2858
Parking light deactivation with direction indicator stalk

## R2859
- _Procedure: 1.Enable parking light function(Ignition status = 2 && NDISwitch=3||1)
  2.Set NDISwitch! = 3||1

## R2860
- _Pass criteria: 1.ParkingLightActive = True,
  Side lights, Side Marker and Tail lamps shall active when parking ligts are activated
  2.ParkingLightAvailable = False,
  Side lights, Side Marker and Tail lamps are OFF

## R2861
- _Regression: No

## R2862
- _Time [hr]: 0.1

## R2863
- _Test environment: Lab-Car (auto)

## STC-BDY02-371

## R2865
- _Object type: Negative Test

## R2866
- _Status: REVIEWED

## R2867: Parking light deactivation

## R2868
Parking light deactivation when battery is very low SOC

## R2869
- _Procedure: 1.Enable parking light function(Ignition status = 2 && NDISwitch=3||1)
  2.Set INBatteryLowStateOfCharge = 1||2

## R2870
- _Pass criteria: 1.ParkingLightActive = True,
  Side lights, Side Marker and Tail lamps shall active when parking ligts are activated
  2.ParkingLightAvailable = False,
  Side lights, Side Marker and Tail lamps are OFF

## R2871
- _Regression: No

## R2872
- _Time [hr]: 0.1

## R2873
- _Test environment: Lab-Car (auto)

## STC-BDY02-367

## R2875
- _Object type: Nominal Test

## R2876
- _Status: REVIEWED

## R2877: Parking light function NOT available

## R2878
Parking light function NOT available when ignition state>2

## R2879
- _Procedure: 1.Set ignition status > 2
  2.Set direction Indicator stalk in either left or right position (NDISwitch=3||1)

## R2880
- _Pass criteria: ParkingLightAvailable = False,
  Side lights, Side Marker and Tail lamps shall remain OFF

## R2881
- _Regression: No

## R2882
- _Time [hr]: 0.1

## R2883
- _Test environment: Lab-Car (auto)

## STC-BDY02-362

## R2885
- _Object type: Nominal Test

## R2886
- _Status: REVIEWED

## R2887: Parking light activation

## R2888
Parking light activation

## R2889
- _Procedure: 1.Set ignition status = 2
  2.Set direction Indicator stalk in either left or right position (NDISwitch=3||1)

## R2890
- _Pass criteria: ParkingLightActive = True,
  Side lights, Side Marker and Tail lamps shall active when parking ligts are activated

## R2891
- _Regression: Yes

## R2892
- _Time [hr]: 0.1

## R2893
- _Test environment: Lab-Car (auto)

## STC-BDY02-368

## R2895
- _Object type: Nominal Test

## R2896
- _Status: REVIEWED

## R2897: Parking light function NOT available

## R2898
Parking light function NOT available with direction indicator stalk

## R2899
- _Procedure: 1.Set ignition status = 2
  2.Set NDISwitch!=3||1

## R2900
- _Pass criteria: ParkingLightAvailable = False,
  Side lights, Side Marker and Tail lamps shall remain OFF

## R2901
- _Regression: No

## R2902
- _Time [hr]: 0.1

## R2903
- _Test environment: Lab-Car (auto)

## STC-BDY02-369

## R2905
- _Object type: Nominal Test

## R2906
- _Status: REVIEWED

## R2907: Parking light function NOT available

## R2908
Parking light function NOT available with low SOC

## R2909
- _Procedure: 1.Set NIgnitionStatus = Awake || Accessory
  2. Set NBatteryLowStateOfCharge != OK
  3.Set NDISwitch=3||1

## R2910
- _Pass criteria: ParkingLightAvailable = False,
  Side lights, Side Marker and Tail lamps shall remain OFF

## R2911
- _Regression: No

## R2912
- _Time [hr]: 0.1

## R2913
- _Test environment: Lab-Car (auto)

## STC-BDY02-513

## R2915
- _Object type: Nominal Test

## R2916
- _Status: REVIEWED

## R2917: Parking Light Left Active

## R2918
Parking Light Left Activation

## R2919
- _Procedure: 1.Set NIgnitionStatus =2
  2. Parking Light Function Available && NDISwitch == Downwards

## R2920
- _Pass criteria: NSideLightLeftStatus = Active
  NTailLightLeftStatus = Active
  BParkingLightStatus = Active

## R2921
- _Regression: Yes

## R2922
- _Time [hr]: 0.2

## R2923
- _Test environment: Lab-Car (auto)

## STC-BDY02-532

## R2925
- _Object type: Nominal Test

## R2926
- _Status: REVIEWED

## R2927: Parking Light Left deActive with ignition state

## R2928
Parking Light Left deActivation when existing current ignition state

## R2929
- _Procedure: 1.Set NIgnitionStatus =2 && Parking lights Inactive
  2.Operate Direction Indicator stalk to Left position, NDISwitch = 1 ( Rising edge)
  3.Set NIgnitionStatus > 2

## R2930
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Left front Side Lamp, left Side Markers and left rear Tail Lamp shall be deactivated.
  ParkingLightLeftActive= False,
  NSideLStatus=0x0,
  NSidemarkerLeftStatus= 0x0,
  NTailLightLStatus= 0x0,
  NParkingLightsStaus = 0x00( both OFF)

## R2931
- _Regression: No

## R2932
- _Time [hr]: 0.2

## R2933
- _Test environment: Lab-Car (auto)

## STC-BDY02-534

## R2935
- _Object type: Nominal Test

## R2936
- _Status: REVIEWED

## R2937: Parking Light Left deActive with low battery value

## R2938
Parking Light Left deActivation with low battery voltage

## R2939
- _Procedure: 1.Set NIgnitionStatus =2 && Parking lights Inactive
  2.Operate Direction Indicator stalk to Left position, NDISwitch = 1 ( Rising edge)
  3.Set NBatteryUVP = 1||2

## R2940
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Left front Side Lamp, left Side Markers and left rear Tail Lamp shall be deactivated.
  ParkingLightLeftActive= False,
  NSideLStatus=0x0,
  NSidemarkerLeftStatus= 0x0,
  NTailLightLStatus= 0x0,
  NParkingLightsStaus = 0x00( both OFF)

## R2941
- _Regression: No

## R2942
- _Time [hr]: 0.2

## R2943
- _Test environment: Lab-Car (auto)

## STC-BDY02-518

## R2945
- _Object type: Nominal Test

## R2946
- _Status: REVIEWED

## R2947: Parking Light Right Active

## R2948
Parking Light Right Activation

## R2949
- _Procedure: 1.Set NIgnitionStatus =2 && Parking lights Inactive
  2.Operate Direction Indicator stalk to Right position, NDISwitch = 3 ( Rising edge)

## R2950
- _Pass criteria: Right front Side Lamp, Right Side Markers and Right rear Tail Lamp shall be activated.
  ParkingLightRightActive= True,
  NSideRStatus=0x1,
  NSidemarkerRightStatus= 0x1,
  NTailLightLStatus= 0x1,
  NParkingLightsStaus = 0x02( right on)

## R2951
- _Regression: Yes

## R2952
- _Time [hr]: 0.2

## R2953
- _Test environment: Lab-Car (auto)

## STC-BDY02-533

## R2955
- _Object type: Nominal Test

## R2956
- _Status: REVIEWED

## R2957: Parking Light Right deActive with ignition state

## R2958
Parking Light Right deActivation when existing current ignition state

## R2959
- _Procedure: 1.Set NIgnitionStatus =2 && Parking lights Inactive
  2.Operate Direction Indicator stalk to Right position, NDISwitch = 3 ( Rising edge)
  3.Set NIgnitionStatus > 2

## R2960
- _Pass criteria: 2.Right front Side Lamp, Right Side Markers and Right rear Tail Lamp shall be activated.
  ParkingLightRightActive= True,
  NSideRStatus=0x1,
  NSidemarkerRightStatus= 0x1,
  NTailLightLStatus= 0x1,
  NParkingLightsStaus = 0x02( right on)
  3.Right front Side Lamp, Right Side Markers and Right rear Tail Lamp shall be deactivated.
  ParkingLightRightActive= False,
  NSideRStatus=0x0,
  NSidemarkerRightStatus= 0x0,
  NTailLightLStatus= 0x0,
  NParkingLightsStaus = 0x00( both OFF)

## R2961
- _Regression: No

## R2962
- _Time [hr]: 0.2

## R2963
- _Test environment: Lab-Car (auto)

## STC-BDY02-535

## R2965
- _Object type: Nominal Test

## R2966
- _Status: REVIEWED

## R2967: Parking Light Right deActive with low battery value

## R2968
Parking Light Right deActivation with low battery voltage

## R2969
- _Procedure: 1.Set NIgnitionStatus =2 && Parking lights Inactive
  2.Operate Direction Indicator stalk to Right position, NDISwitch = 3 ( Rising edge)
  3.Set NBatteryUVP = 1||2

## R2970
- _Pass criteria: 2.Right front Side Lamp, Right Side Markers and Right rear Tail Lamp shall be activated.
  ParkingLightRightActive= True,
  NSideRStatus=0x1,
  NSidemarkerRightStatus= 0x1,
  NTailLightLStatus= 0x1,
  NParkingLightsStaus = 0x02( right on)
  3.Right front Side Lamp, Right Side Markers and Right rear Tail Lamp shall be deactivated.
  ParkingLightRightActive= False,
  NSideRStatus=0x0,
  NSidemarkerRightStatus= 0x0,
  NTailLightLStatus= 0x0,
  NParkingLightsStaus = 0x00( both OFF)

## R2971
- _Regression: No

## R2972
- _Time [hr]: 0.2

## R2973
- _Test environment: Lab-Car (auto)

## STC-BDY02-514

## R2975
- _Object type: Nominal Test

## R2976
- _Status: REVIEWED

## R2977: Left & Right Parking Lights active

## R2978
Both Left & Right Parking Lights activation

## R2979
- _Procedure: 1.Set NIgnitionStatus =2 && Parking lights Inactive
  2.Operate Direction Indicator Stalk in both directions just once i.e.,
  NDISwitch = 1 ( Rising edge) &&
  NDISwitch = 3 (Rising edge)

## R2980
- _Pass criteria: Both left and right parking lights shall be activated.
  ParkingLightBothActive= True,
  NSideLStatus=0x1,
  NSidemarkerLeftStatus= 0x1,
  NTailLightLStatus= 0x1,
  NSideRStatus=0x1,
  NSidemarkerRightStatus= 0x1,
  NTailLightLStatus= 0x1,
  NParkingLightsStaus = 0x03( both on)

## R2981
- _Regression: Yes

## R2982
- _Time [hr]: 0.4

## R2983
- _Test environment: Lab-Car (auto)

## STC-BDY02-536

## R2985
- _Object type: Nominal Test

## R2986
- _Status: REVIEWED

## R2987: Left & Right Parking Lights deactive with ignition state

## R2988
Both Left & Right Parking Lights deactivation while exiting current ignition state

## R2989
- _Procedure: 1.Set NIgnitionStatus =2 && Parking lights Inactive
  2.Operate Direction Indicator Stalk in both directions just once i.e.,
  NDISwitch = 1 ( Rising edge) &&
  NDISwitch = 3 (Rising edge)
  3.Set NIgnitionStatus > 2

## R2990
- _Pass criteria: 2.Both left and right parking lights shall be activated.
  ParkingLightBothActive= True,
  NSideLStatus=0x1,
  NSidemarkerLeftStatus= 0x1,
  NTailLightLStatus= 0x1,
  NSideRStatus=0x1,
  NSidemarkerRightStatus= 0x1,
  NTailLightLStatus= 0x1,
  NParkingLightsStaus = 0x03( both on)
  3.Both left and right parking lights shall be deactivated.
  ParkingLightBothActive= False,
  NSideLStatus=0x0,
  NSidemarkerLeftStatus= 0x0,
  NTailLightLStatus= 0x0,
  NSideRStatus=0x0,
  NSidemarkerRightStatus= 0x0,
  NTailLightLStatus= 0x0,
  NParkingLightsStaus = 0x00( both OFF)

## R2991
- _Regression: No

## R2992
- _Time [hr]: 0.4

## R2993
- _Test environment: Lab-Car (auto)

## STC-BDY02-537

## R2995
- _Object type: Nominal Test

## R2996
- _Status: REVIEWED

## R2997: Left & Right Parking Lights deactive with low battery value

## R2998
Both Left & Right Parking Lights deactivation with low battery voltage

## R2999
- _Procedure: 1.Set NIgnitionStatus =2 && Parking lights Inactive
  2.Operate Direction Indicator Stalk in both directions just once i.e.,
  NDISwitch = 1 ( Rising edge) &&
  NDISwitch = 3 (Rising edge)
  3.Set NBatteryUVP = 1||2

## R3000
- _Pass criteria: 2.Both left and right parking lights shall be activated.
  ParkingLightBothActive= True,
  NSideLStatus=0x1,
  NSidemarkerLeftStatus= 0x1,
  NTailLightLStatus= 0x1,
  NSideRStatus=0x1,
  NSidemarkerRightStatus= 0x1,
  NTailLightLStatus= 0x1,
  NParkingLightsStaus = 0x03( both on)
  3.Both left and right parking lights shall be deactivated.
  ParkingLightBothActive= False,
  NSideLStatus=0x0,
  NSidemarkerLeftStatus= 0x0,
  NTailLightLStatus= 0x0,
  NSideRStatus=0x0,
  NSidemarkerRightStatus= 0x0,
  NTailLightLStatus= 0x0,
  NParkingLightsStaus = 0x00( both OFF)

## R3001
- _Regression: No

## R3002
- _Time [hr]: 0.4

## R3003
- _Test environment: Lab-Car (auto)

## STC-BDY02-519

## R3005
- _Object type: Nominal Test

## R3006
- _Status: REVIEWED

## R3007: Parking Light Left deactive

## R3008
Parking Light Left deactivation

## R3009
- _Procedure: 1.Set NIgnitionStatus =2 && Parking lights Inactive
  2.Operate Direction Indicator stalk to Left position, ParkingLightLeftActive= True && NDISwitch = 1 ( Rising edge)
  3.Operate Direction indicator again to same side, NDISwitch = 1 ( Rising edge)

## R3010
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Parking light on that side(left) shall be deactivated.
  ParkingLightLeftActive= False
  NSideLStatus=0x0,
  NSidemarkerLeftStatus= 0x0,
  NTailLightLStatus= 0x0

## R3011
- _Regression: Yes

## R3012
- _Time [hr]: 0.2

## R3013
- _Test environment: Lab-Car (auto)

## STC-BDY02-520

## R3015
- _Object type: Nominal Test

## R3016
- _Status: REVIEWED

## R3017: Parking Light Right deactive

## R3018
Parking Light Right deactivation

## R3019
- _Procedure: 1.Set NIgnitionStatus =2 && Parking lights Inactive
  2.Operate Direction Indicator stalk to Right position, ParkingLightRightActive= True && NDISwitch = 3 ( Rising edge)
  3.Operate Direction indicator again to same side, NDISwitch = 3 ( Rising edge)

## R3020
- _Pass criteria: 2.Right front Side Lamp, Right Side Markers and Right rear Tail Lamp shall be activated.
  ParkingLightRightActive= True,
  NSideRStatus=0x1,
  NSidemarkerRightStatus= 0x1,
  NTailLightRStatus= 0x1,
  NParkingLightsStaus = 0x02( Right on)
  3.Parking light on that side(Right ) shall be deactivated.
  ParkingLightRight Active= False
  NSideRStatus=0x0,
  NSidemarkerRightStatus= 0x0,
  NTailLightRStatus= 0x0

## R3021
- _Regression: Yes

## R3022
- _Time [hr]: 0.2

## R3023
- _Test environment: Lab-Car (auto)

## STC-BDY02-523

## R3025
- _Object type: Nominal Test

## R3026
- _Status: REVIEWED

## R3027: Left parking light activation with Right light already in active state

## R3028
Left Parking Light activation while Right light was in active state

## R3029
- _Procedure: 1.Set NIgnitionStatus =2 && Parking lights Inactive
  2.Operate Direction indicator to Right side, NDISwitch = 3 ( Rising edge)
  3.Operate Direction indicator to Left side, NDISwitch = 1 ( Rising edge)

## R3030
- _Pass criteria: 2.Right front Side Lamp, Right Side Markers and Right rear Tail Lamp shall be activated.
  ParkingLightRightActive= True,
  NSideRStatus=0x1,
  NSidemarkerRightStatus= 0x1,
  NTailLightLStatus= 0x1,
  NParkingLightsStaus = 0x02( right on)
  3.Both left and right parking lights shall be activated.
  ParkingLightBothActive= True,
  NSideLStatus=0x1,
  NSidemarkerLeftStatus= 0x1,
  NTailLightLStatus= 0x1,
  NSideRStatus=0x1,
  NSidemarkerRightStatus= 0x1,
  NTailLightRStatus= 0x1,
  NParkingLightsStaus = 0x03( both on)

## R3031
- _Regression: No

## R3032
- _Time [hr]: 0.2

## R3033
- _Test environment: Lab-Car (auto)

## STC-BDY02-524

## R3035
- _Object type: Nominal Test

## R3036
- _Status: REVIEWED

## R3037: Right parking light activation with Left light already in active state

## R3038
Right Parking Light activation while Left light was in active state

## R3039
- _Procedure: 1.Set NIgnitionStatus =2 && Parking lights Inactive
  2.Operate Direction indicator to Left side, NDISwitch = 1 ( Rising edge)
  3.Operate Direction indicator to Right side, NDISwitch = 3 ( Rising edge)

## R3040
- _Pass criteria: 2.Left front Side Lamp, left Side Markers and left rear Tail Lamp shall be activated.
  ParkingLightLeftActive= True,
  NSideLStatus=0x1,
  NSidemarkerLeftStatus= 0x1,
  NTailLightLStatus= 0x1,
  NParkingLightsStaus = 0x01( left on)
  3.Both left and right parking lights shall be activated.
  ParkingLightBothActive= True,
  NSideLStatus=0x1,
  NSidemarkerLeftStatus= 0x1,
  NTailLightLStatus= 0x1,
  NSideRStatus=0x1,
  NSidemarkerRightStatus= 0x1,
  NTailLightRStatus= 0x1,
  NParkingLightsStaus = 0x03( both on)

## R3041
- _Regression: No

## R3042
- _Time [hr]: 0.2

## R3043
- _Test environment: Lab-Car (auto)

## STC-BDY02-525

## R3045
- _Object type: Nominal Test

## R3046
- _Status: REVIEWED

## R3047: Both Parking Lights deactive

## R3048
Both Left & Right Parking Lights (Right followed by Left)deactivation when both parking lights are active

## R3049
- _Procedure: 1.Set NIgnitionStatus =2 && Parking lights Inactive
  2.Operate Direction Indicator Stalk in both directions just once i.e.,
  NDISwitch = 1 ( Rising edge) &&
  NDISwitch = 3 (Rising edge)
  3.Operate Direction indicator to Left side, NDISwitch = 1 ( Rising edge)
  4.Operate Direction indicator to Right side, NDISwitch = 3 ( Rising edge)

## R3050
- _Pass criteria: 2.Both left and right parking lights shall be activated.
  ParkingLightBothActive= True,
  NSideLStatus=0x1,
  NSidemarkerLeftStatus= 0x1,
  NTailLightLStatus= 0x1,
  NSideRStatus=0x1,
  NSidemarkerRightStatus= 0x1,
  NTailLightRStatus= 0x1,
  NParkingLightsStaus = 0x03( both on)
  3.Parking light on that side(left) shall be deactivated and Right side shall be in active state.
  ParkingLightLeftActive= False
  NSideLStatus=0x0,
  NSidemarkerLeftStatus= 0x0,
  NTailLightLStatus= 0x0,
  NSideRStatus=0x1,
  NSidemarkerRightStatus= 0x1,
  NTailLightRStatus= 0x1,
  NParkingLightsStaus = 0x02( Right on)
  4.Both left and right parking lights shall be deactivated.
  ParkingLightBothActive= False,
  NSideLStatus=0x0,
  NSidemarkerLeftStatus= 0x0,
  NTailLightLStatus= 0x0,
  NSideRStatus=0x0,
  NSidemarkerRightStatus= 0x0,
  NTailLightRStatus= 0x0,
  NParkingLightsStaus = 0x00( both OFF)

## R3051
- _Regression: No

## R3052
- _Time [hr]: 0.2

## R3053
- _Test environment: Lab-Car (auto)

## STC-BDY02-527

## R3055
- _Object type: Nominal Test

## R3056
- _Status: REVIEWED

## R3057: Left Parking light telltale

## R3058
Left Parking Light status to DriverDisplay

## R3059
- _Procedure: Activate Left Parking light:
  Set NIgnitionStatus =2 && NDISwitch = 1 ( Rising edge)

## R3060
- _Pass criteria: Status of the Left Parking Light shall be communicated to the cluster

## R3061
- _Regression: Yes

## R3062
- _Time [hr]: 0.2

## R3063
- _Test environment: Lab-Car (manual)

## STC-BDY02-528

## R3065
- _Object type: Nominal Test

## R3066
- _Status: REVIEWED

## R3067: Right Parking light telltale

## R3068
Right Parking Light status to DriverDisplay

## R3069
- _Procedure: Activate Right Parking light:
  Set NIgnitionStatus =2 && NDISwitch = 3 ( Rising edge)

## R3070
- _Pass criteria: Status of the Right Parking Light shall be communicated to the cluster

## R3071
- _Regression: Yes

## R3072
- _Time [hr]: 0.2

## R3073
- _Test environment: Lab-Car (manual)

## STC-BDY02-515

## R3075
- _Object type: Nominal Test

## R3076
- _Status: REVIEWED

## R3077: Parking lights telltale

## R3078
Left & Right Parking Lights status to DriverDisplay

## R3079
- _Procedure: Activate Left & Right Parking light:
  Set NIgnitionStatus =2 && NDISwitch = 1 ( Rising edge) && NDISwitch = 3 ( Rising edge)

## R3080
- _Pass criteria: Status of the both Left & Right Parking Lights shall be communicated to the cluster

## R3081
- _Regression: Yes

## R3082
- _Time [hr]: 0.2

## R3083
- _Test environment: Lab-Car (manual)

## STC-BDY02-529

## R3085
- _Object type: Nominal Test

## R3086
- _Status: REVIEWED

## R3087: DCU awake with Left parking light

## R3088
DCU shall stay awake in ignition 0,1 while Left parking light is active

## R3089
- _Procedure: 1.Activate Left Parking light:
  Set NIgnitionStatus =2 && NDISwitch = 1 ( Rising edge)
  2.Deactive Left Parking light:NDISwitch = 1 ( Rising edge)

## R3090
- _Pass criteria:
  1. DCU shall stay awake in Ignition 0,1 until left parking light is active
  2.DCU shall no longer be awake

## R3091
- _Regression: No

## R3092
- _Time [hr]: 0.2

## R3093
- _Test environment: Lab-Car (manual)

## STC-BDY02-530

## R3095
- _Object type: Nominal Test

## R3096
- _Status: REVIEWED

## R3097: DCU awake with Right parking light

## R3098
DCU shall stay awake in ignition 0,1 while Right parking light is active

## R3099
- _Procedure: 1.Activate Right Parking light:
  Set NIgnitionStatus =2 && NDISwitch = 3 ( Rising edge)
  2.Deactive Right Parking light:NDISwitch = 3 ( Rising edge)

## R3100
- _Pass criteria:
  1. DCU shall stay awake in Ignition 0,1 until Right parking light is active
  2.DCU shall no longer be awake

## R3101
- _Regression: No

## R3102
- _Time [hr]: 0.2

## R3103
- _Test environment: Lab-Car (manual)

## STC-BDY02-531

## R3105
- _Object type: Nominal Test

## R3106
- _Status: REVIEWED

## R3107: DCU awake with parking lights

## R3108
DCU shall stay awake in ignition 0,1 while parking lights are active

## R3109
- _Procedure: 1.Activate Parking lights:
  Set NIgnitionStatus =2 && NDISwitch = 1 ( Rising edge) && NDISwitch = 3 ( Rising edge)
  2.Deactive Left Parking light: NDISwitch = 1 ( Rising edge)
  3.Deactive Right Parking light: NDISwitch = 3 ( Rising edge)

## R3110
- _Pass criteria:
  1. DCU shall stay awake in Ignition 0,1 until any of the parking light is active
  2.DCU shall stay awake in Ignition 0,1 until any of the parking light is active
  3.DCU shall no longer be awake

## R3111
- _Regression: No

## R3112
- _Time [hr]: 0.2

## R3113
- _Test environment: Lab-Car (manual)

## STC-BDY02-238

## R3115
- _Object type: Fault Test

## R3116
- _Status: REVIEWED

## R3117: LH brake/Tail lamp output - S/C(GND)

## R3118
DTC B122211 for LH brake/Tail lamp output is short to ground

## R3119
- _Procedure: 1.Set ignition state to 1
  2.Short LH brake/Tail lamp output pin(xx) to ground(xx) for a duration of fault calibratable debounce period
  3.Remove the short b/w ouput pin to ground after fault calibratable debounce period
  4.Repeat steps 2,3 for all the ignition states

## R3120
- _Pass criteria: 2.DTC B122211 shall be logged in current state in ZC1.
  Check cluster message CAN value.
  3.DTC B122211 shall be in healed state in ZC1.
  No cluster message CAN value.

## R3121
- _Regression: No

## R3122
- _Time [hr]: 0.4

## R3123
- _Test environment: Lab-Car (auto)

## STC-BDY02-239

## R3125
- _Object type: Fault Test

## R3126
- _Status: REVIEWED

## R3127: RH brake/Tail lamp output - S/C(GND)

## R3128
DTC B12111 RH brake/Tail lamp output is short to ground

## R3129
- _Procedure: 1.Set ignition state to 1
  2.Short RH brake/Tail lamp output pin(xx) to ground(xx) for a duration of fault calibratable debounce period
  3.Remove the short b/w ouput pin to ground after fault calibratable debounce period
  4.Repeat steps 2,3 for all the ignition states

## R3130
- _Pass criteria: 2.DTC B12111 shall be logged in current state in ZC1.
  Check cluster message CAN value.
  3.DTC B12111 shall be in healed state in ZC1.
  No cluster message CAN value.

## R3131
- _Regression: No

## R3132
- _Time [hr]: 0.4

## R3133
- _Test environment: Lab-Car (auto)

## STC-BDY02-240

## R3135
- _Object type: Fault Test

## R3136
- _Status: REVIEWED

## R3137: Master light switch - voltage out of range

## R3138
DTC B12011C Master light switch output voltage is out of range

## R3139
- _Procedure: 1.Set ignition state to 1
  2.Short the master light switch output pin(xx) to battery voltage pin(xx) or open the output pin(xx) for a duration of fault calibratable debounce period
  3.Remove the short b/w ouput pin to battery after fault calibratable debounce period
  4.Repeat steps 2,3 for all the ignition states

## R3140
- _Pass criteria: 2.DTC B12011Cshall be logged in current state in ZC1.
  Check cluster message CAN value.
  3.DTC B12011C shall be in healed state in ZC1.
  No cluster message CAN value.

## R3141
- _Regression: No

## R3142
- _Time [hr]: 0.4

## R3143
- _Test environment: Lab-Car (auto)

## STC-BDY02-241

## R3145
- _Object type: Fault Test

## R3146
- _Status: REVIEWED

## R3147: LH LED headlamp - S/C(GND)

## R3148
DTC B122011 LH LED headlamp output short circuit to ground

## R3149
- _Procedure: 1.Set ignition state to 1
  2.Short left hand headlamp output pin(xx) to ground(xx) for a duration of fault calibratable debounce period
  3.Remove the short b/w ouput pin to ground after fault calibratable debounce period
  4.Repeat steps 2,3 for all the ignition states

## R3150
- _Pass criteria: 2.DTC B122011 shall be logged in current state in ZA1.
  Check cluster message CAN value.
  3.DTC B122011 shall be in healed state in ZA1.
  No cluster message CAN value.

## R3151
- _Regression: No

## R3152
- _Time [hr]: 0.4

## R3153
- _Test environment: Lab-Car (auto)

## STC-BDY02-243

## R3155
- _Object type: Fault Test

## R3156
- _Status: REVIEWED

## R3157: RH LED headlamp - S/C(GND)

## R3158
DTC B121F11 RH LED headlamp output short circuit to ground

## R3159
- _Procedure: 1.Set ignition state to 1
  2.Short right hand headlamp output pin(xx) to ground(xx) for a duration of fault calibratable debounce period
  3.Remove the short b/w ouput pin to ground after fault calibratable debounce period
  4.Repeat steps 2,3 for all the ignition states

## R3160
- _Pass criteria: 2.DTC B121F11 shall be logged in current state in ZA1.
  Check cluster message CAN value.
  3.DTC B121F11 shall be in healed state in ZA1.
  No cluster message CAN value.

## R3161
- _Regression: No

## R3162
- _Time [hr]: 0.4

## R3163
- _Test environment: Lab-Car (auto)

## STC-BDY02-468

## R3165
- _Object type: Fault Test

## R3166
- _Status: REVIEWED

## R3167: Left lamp -shrt to GND

## R3168
Main beam headlamp output left side-short to ground

## R3169
- _Procedure: 1.Set ignition state to 1
  2.Short the main beam headlamp left side output pin(xx) to ground pin(xx) for a duration of fault calibratable debounce period
  3.Remove the short b/w ouput pin to ground after fault calibratable debounce period
  4.Repeat steps 2,3 for all other ignition states

## R3170
- _Pass criteria: 2.DTC XXX shall be logged in current state in ZA1.
  Check for cluster message CAN value.
  3.DTC XXX shall be in healed state in ZA1.
  No cluster message CAN value.

## R3171
- _Regression: No

## R3172
- _Time [hr]: 0.5

## R3173
- _Test environment: Lab-Car (auto)

## STC-BDY02-469

## R3175
- _Object type: Fault Test

## R3176
- _Status: REVIEWED

## R3177: Left lamp -shrt to BATT or Open ckt

## R3178
Main beam headlamp output left side-short to battery or open circuit

## R3179
- _Procedure: 1.Set ignition state to 1
  2.Short the main beam headlamp left side output pin(xx) to battery voltage pin(xx) or open the output pin(xx) for a duration of fault calibratable debounce period
  3.Remove the short b/w ouput pin to battery after fault calibratable debounce period
  4.Repeat steps 2,3 for all other ignition states

## R3180
- _Pass criteria: 2.DTC XXX shall be logged in current state in ZA1.
  Check cluster message CAN value.
  3.DTC XXX shall be in healed state in ZA1.
  No cluster message CAN value.

## R3181
- _Regression: No

## R3182
- _Time [hr]: 0.5

## R3183
- _Test environment: Lab-Car (auto)

## STC-BDY02-470

## R3185
- _Object type: Fault Test

## R3186
- _Status: REVIEWED

## R3187: Right lamp -shrt to GND

## R3188
Main beam headlamp output right side-short to ground

## R3189
- _Procedure: 1.Set ignition state to 1
  2.Short the main beam headlamp right side output pin(xx) to ground pin(xx) for a duration of fault calibratable debounce period
  3.Remove the short b/w ouput pin to ground after fault calibratable debounce period
  4.Repeat steps 2,3 for all other ignition states

## R3190
- _Pass criteria: 2.DTC XXX shall be logged in current state in ZA1.
  Check cluster message CAN value.
  3.DTC XXX shall be in healed state in ZA1.
  No cluster message CAN value.

## R3191
- _Regression: No

## R3192
- _Time [hr]: 0.5

## R3193
- _Test environment: Lab-Car (auto)

## STC-BDY02-471

## R3195
- _Object type: Fault Test

## R3196
- _Status: REVIEWED

## R3197: Right lamp -shrt to BATT or Open ckt

## R3198
Main beam headlamp output rught side-short to battery or open circuit

## R3199
- _Procedure: 1.Set ignition state to 1
  2.Short the main beam headlamp right side output pin(xx) to battery voltage pin(xx) or open the output pin(xx) for a duration of fault calibratable debounce period
  3.Remove the short b/w ouput pin to battery after fault calibratable debounce period
  4.Repeat steps 2,3 for all other ignition states

## R3200
- _Pass criteria: 2.DTC XXX shall be logged in current state in ZA1.
  Check for cluster message CAN value.
  3.DTC XXX shall be in healed state in ZA1.
  No cluster message CAN value.

## R3201
- _Regression: No

## R3202
- _Time [hr]: 0.5

## R3203
- _Test environment: Lab-Car (auto)

## STC-BDY02-1368

## R3205
- _Object type: Misuse Test

## R3206
- _Status: REVIEWED

## R3207: SW Composition ExteriorLightingSafetyZa1

## R3208
Composition Check

## R3209
- _Procedure: The SW composition ExteriorLightingSafetyZa1 implementing the safety monitoring of this function is designed.

## R3210
- _Pass criteria: Verify that the SW composition is the only connected to the actuations of the outputs.

## R3211
- _Regression: No

## R3212
- _Time [hr]: 0.1

## R3213
- _Test environment: HIL (manual)

## STC-BDY02-1503

## R3215
- _Object type: Misuse Test

## R3216
- _Status: REVIEWED

## R3217: SW Composition Master Light Control

## R3218
Composition Check

## R3219
- _Procedure: The SW composition Master Light Control is defined.

## R3220
- _Pass criteria: Verify that the compositions Master Light Control is not connected to any actuation of the outputs.

## R3221
- _Regression: No

## R3222
- _Time [hr]: 0.1

## R3223
- _Test environment: HIL (manual)

## STC-BDY02-1369

## R3225
- _Object type: Misuse Test

## R3226
- _Status: REVIEWED

## R3227: High Side Command Headlamp

## R3228
The ExteriorLightingSafetyZa1 command :
Headlamp_Ctrl_PWR_RH (HSD11_2)
Headlamp_Ctrl_PWR_LH (HSD11_1)
Headlamp_Relay_2_Ctrl (HB5A)
as requested by:
BLH_DippedBeamActivate_Req AND
BRH_DippedBeamActivate_Req during all times

## R3229
- _Procedure: Test Steps :
  BLH_DippedBeamActivate_Req
  BRH_DippedBeamActivate_Req
  during all NIgnitionStatus 0x05 when moniroting is not active

## R3230
- _Pass criteria: Verify that :
  Headlamp_Ctrl_PWR_RH (HSD11_2)
  Headlamp_Ctrl_PWR_LH (HSD11_1
  Headlamp_Relay_2_Ctrl (HB5A)

## R3231
- _Regression: No

## R3232
- _Time [hr]: 0.1

## R3233
- _Test environment: HIL (manual)

## STC-BDY02-1505

## R3235
- _Object type: Misuse Test

## R3236
- _Status: REVIEWED

## R3237: Main beam activation

## R3238
The ExteriorLightingSafetyZa1 shall command
Headlamp_Relay_2_Ctrl (HB5A)
as requested by
BFrontLampPWRSupply_Req during all times

## R3239
- _Procedure: Test Steps :
  BFrontLampPWRSupply_Req
  during all NIgnitionStatus 0x05 when moniroting is not active

## R3240
- _Pass criteria: Verify that :
  Headlamp_Relay_2_Ctrl (HB5A) as commanded

## R3241
- _Regression: No

## R3242
- _Time [hr]: 0.1

## R3243
- _Test environment: Lab-Car (manual)

## STC-BDY02-1370

## R3245
- _Object type: Misuse Test

## R3246
- _Status: REVIEWED

## R3247: MasterLightSwitch in Dipped Beam On Status

## R3248
The ExteriorLightingSafetyZa1 detect when all the below occur:
NMasterLightSwitchStatusFuSa = 0x4 (DIPPED BEAM ON)
BLH_DippedBeamActivate_Req = "no activation request"
BRH_DippedBeamActivate_Req = "no activation request"
NIgnitionStatus ==0x5 (Ignition)
within DTI = 100ms.

## R3249
- _Procedure: Test Steps :
  NMasterLightSwitchStatusFuSa = 0x4 (DIPPED BEAM ON) && BLH_DipperBeamActivate_Req = No activation request & BRH_DippedBeamActivate_Req = No activation request &&
  NIgnitionStatus ==0x5

## R3250
- _Pass criteria: Verify that :
  Headlamp_Ctrl_PWR_RH (HSD11_2) = 100 % duty cycle command &&
  Headlamp_Ctrl_PWR_LH (HSD11_1) = 100% duty cycle && Headlamp_Relay_2_Ctrl (HB5A) = HIgh

## R3251
- _Regression: No

## R3252
- _Time [hr]: 0.1

## R3253
- _Test environment: HIL (manual)

## STC-BDY02-1506

## R3255
- _Object type: Misuse Test

## R3256
- _Status: REVIEWED

## R3257: MasterLightSwitchFault in Active Status

## R3258
The ExteriorLightingSafetyZa1 shall detect when all the below occur:
BMasterLightSwitchFaultStatusFuSa = Active
BLH_DippedBeamActivate_Req = "no activation request"
BRH_DippedBeamActivate_Req = "no activation request"
NIgnitionStatus ==0x5 (Ignition)
within DTI = 100ms.

## R3259
- _Procedure: Test Steps :
  BMasterLightSwitchFaultStatusFuSa = Active && BLH_DipperBeamActivate_Req = No activation request & BRH_DippedBeamActivate_Req = No activation request &&
  NIgnitionStatus ==0x5

## R3260
- _Pass criteria: Verify that :
  Headlamp_Ctrl_PWR_RH (HSD11_2) = 100 % duty cycle command &&
  Headlamp_Ctrl_PWR_LH (HSD11_1) = 100% duty cycle
  Headlamp_Relay_2_Ctrl (HB5A) = HIgh

## R3261
- _Regression: No

## R3262
- _Time [hr]: 0.1

## R3263
- _Test environment: HIL (manual)

## STC-BDY02-1507

## R3265
- _Object type: Misuse Test

## R3266
- _Status: REVIEWED

## R3267: Safe State #BDY02_FL_1

## R3268
Upon detection of [STC-BDY02-1370] or [STC-BDY02-1506] the ExteriorLightingSafetyZa1 transition to Safe State #BDY02_FL_1.

## R3269
- _Procedure: Test Steps :
  NMasterLightSwitchStatusFuSa = 0x4 (DIPPED BEAM ON) && BLH_DipperBeamActivate_Req = No activation request & BRH_DippedBeamActivate_Req = No activation request

## R3270
- _Pass criteria: Verify that :
  Headlamp_Ctrl_PWR_RH (HSD11_2) = 100 % duty cycle command &&
  Headlamp_Ctrl_PWR_LH (HSD11_1) = 100% duty cycle && Headlamp_Relay_2_Ctrl (HB5A) = HIgh

## R3271
- _Regression: No

## R3272
- _Time [hr]: 0.1

## R3273
- _Test environment: HIL (manual)

## STC-BDY02-1508

## R3275
- _Object type: Misuse Test

## R3276
- _Status: REVIEWED

## R3277: Critical temperature threshold

## R3278
No action is to be taken when DcuMonTemperatureSafetyMaskZa1 = Critical temperature threshold.

## R3279
- _Procedure: DcuMonTemperatureSafetyMaskZa1 = Critical temperature threshold.

## R3280
- _Pass criteria: No reaction.

## R3281
- _Regression: No

## R3282
- _Time [hr]: 0.1

## R3283
- _Test environment: HIL (manual)

## STC-BDY02-1371

## R3285
- _Object type: Misuse Test

## R3286
- _Status: REVIEWED

## R3287: High Side Command Headlamp with with max duty

## R3288
Headlamp duty command

## R3289
- _Procedure: The ExteriorLightingSafetyZa1 command 100% duty cycle the outputs:
  Headlamp_Ctrl_PWR_RH (HSD11_2)
  Headlamp_Ctrl_PWR_LH (HSD11_1)

## R3290
- _Pass criteria: Verify that both Headlamps are lighted on.

## R3291
- _Regression: No

## R3292
- _Time [hr]: 0.1

## R3293
- _Test environment: HIL (manual)

## STC-BDY02-1509

## R3295
- _Object type: Misuse Test

## R3296
- _Status: REVIEWED

## R3297: High Side Command Headlamp with with relay

## R3298
Headlamp relay command

## R3299
- _Procedure: The ExteriorLightingSafetyZa1 command "High side activated":
  Headlamp_Relay_2_Ctrl (HB5A)

## R3300
- _Pass criteria: Verify that both Headlamps are lighted on.

## R3301
- _Regression: No

## R3302
- _Time [hr]: 0.1

## R3303
- _Test environment: HIL (manual)

## STC-BDY02-1510

## R3305
- _Object type: Misuse Test

## R3306
- _Status: REVIEWED

## R3307: ElcSafety

## R3308
ElcSafety command safety signals

## R3309
- _Procedure: The ElcSafety command the below signal:
  NFlcSafetyClusterMessage = "fault value"
  FlcSafetyStatusMask = TBD (specific fault detected i.e. short to gound, battery, open, etc.)

## R3310
- _Pass criteria: Verify that both signal are activated.

## R3311
- _Regression: No

## R3312
- _Time [hr]: 0.1

## R3313
- _Test environment: HIL (manual)

## STC-BDY02-1372

## R3315
- _Object type: Misuse Test

## R3316
- _Status: REVIEWED

## R3317: Safe State #BDY02_FL_1 Action

## R3318
While in Safe State #BDY02_FL_1, the ExteriorLightingSafetyZa1 perform the action specified in [STC-BDY02-1371], [STC-BDY02-1509] within FRT = 100 ms.

## R3319
- _Procedure: Test Steps :
  Master Light switch status = Step4 && BLH_DipperBeamActivate_Req = No activation request & BRH_DipperBeamActivate_Req = No activation request
  HW failures (i.e. short to ground, open, short to battery, out of range) on the signal specified in [1334]

## R3320
- _Pass criteria: Verify that Dipped Beam is activated.

## R3321
- _Regression: No

## R3322
- _Time [hr]: 0.1

## R3323
- _Test environment: HIL (manual)

## STC-BDY02-1511

## R3325
- _Object type: Misuse Test

## R3326
- _Status: REVIEWED

## R3327: Safe State #BDY02_FL_1 exit condition

## R3328
The ExteriorLightingSafetyZa1 exit Safe State #BDY02_FL_1 at the new vehicle ignition cycle or after a healing time interval, HTI= 3 secs, when the fault no longer exists.

## R3329
- _Procedure: Next Ignition Cycle OR HTI=3s

## R3330
- _Pass criteria: Verify that exit Safe State #BDY02_2 and Normal Operation of ElcSafety.

## R3331
- _Regression: No

## R3332
- _Time [hr]: 0.1

## R3333
- _Test environment: HIL (manual)

## STC-BDY02-1374

## R3335
- _Object type: Misuse Test

## R3336
- _Status: REVIEWED

## R3337: Safe State #BDY02_FL_2 Action

## R3338
While in Safe State #BDY02_FL_2 , the ExteriorLightingSafetyZa1 perform the action specified in [STC-BDY02-1510] within FRT = 100 ms.

## R3339
- _Procedure: Test Steps :
  HW failures (i.e. short to ground, open, short to battery, out of range) on the signal specified in [1341] OR
  No command to activate Dipped beam

## R3340
- _Pass criteria: Verify that the warning sent to driver.

## R3341
- _Regression: No

## R3342
- _Time [hr]: 0.1

## R3343
- _Test environment: HIL (manual)

## STC-BDY02-1376

## R3345
- _Object type: Misuse Test

## R3346
- _Status: REVIEWED

## R3347: Safe State #BDY02_FL_2 exit condition

## R3348
The ExteriorLightingSafetyZa1 exit Safe State #BDY02_FL_2 at the new vehicle ignition cycle or after a healing time interval, HTI= 3 secs, when the fault no longer exists.

## R3349
- _Procedure: Next Ignition Cycle OR HTI=3s

## R3350
- _Pass criteria: Verify that exit Safe State #BDY02_3 and Normal Operation of ElcSafety.

## R3351
- _Regression: No

## R3352
- _Time [hr]: 0.1

## R3353
- _Test environment: HIL (manual)

## STC-BDY02-1515

## R3355
- _Object type: Misuse Test

## R3356
- _Status: REVIEWED

## R3357: Safe State #BDY02_FL_3 Action

## R3358
While in Safe State #BDY02_FL_3 , the ExteriorLightingSafetyZa1 perform the action specified in [STC-BDY02-1510] within FRT = 100 ms.

## R3359
- _Procedure: Test Steps :
  HW failures (i.e. short to ground, open, short to battery, out of range) on the signal specified in [1341] OR
  No command to activate Dipped beam

## R3360
- _Pass criteria: Verify that the warning sent to driver and request of emergency activation to ZB1.

## R3361
- _Regression: No

## R3362
- _Time [hr]: 0.1

## R3363
- _Test environment: HIL (manual)

## STC-BDY02-1517

## R3365
- _Object type: Misuse Test

## R3366
- _Status: REVIEWED

## R3367: Safe State #BDY02_FL_3 exit condition

## R3368
The ExteriorLightingSafetyZa1 exit Safe State #BDY02_FL_3 at the new vehicle ignition cycle or after a healing time interval, HTI= 3 secs, when the fault no longer exists.

## R3369
- _Procedure: Next Ignition Cycle OR HTI=3s

## R3370
- _Pass criteria: Verify that exit Safe State #BDY02_3 and Normal Operation of ElcSafety.

## R3371
- _Regression: No

## R3372
- _Time [hr]: 0.1

## R3373
- _Test environment: HIL (manual)

## STC-BDY02-1381

## R3375
- _Object type: Misuse Test

## R3376
- _Status: REVIEWED

## R3377: ExteriorLightingSafetyZa1 signal received

## R3378
Signal received check

## R3379
- _Procedure: The ExteriorLightingSafetyZa1 receive the following signals:
  NMasterLightSwitchStatusFuSa
  BMasterLightSwitchFaultStatusFuSa
  EflcSafetyStatusMask
  BLH_DippedBeamActivate_Req
  BRH_DippedBeamActivate_Req
  Headlamp_PWR_Status_RH (DI2)
  Headlamp_PWR_Status_LH (DI1)
  DcuMonTemperatureSafetyMaskZa1
  NIgnitionStatus
  BFrontLampPWRSupply_Req

## R3380
- _Pass criteria: Verify that ExteriorLightingSafetyZa1 receive all signals.
  The message containing the signals :
  NMasterLightSwitchStatusFuSa
  BMasterLightSwitchFaultStatusFuSa
  EflcSafetyStatusMask
  NIgnitionStatus
  is protected with E2E.

## R3381
- _Regression: No

## R3382
- _Time [hr]: 0.1

## R3383
- _Test environment: HIL (manual)

## STC-BDY02-1384

## R3385
- _Object type: Misuse Test

## R3386
- _Status: REVIEWED

## R3387: No activation command to activate dipped beam on driver request

## R3388
The ExteriorLightingSafetyZa1 detect the following:
Headlamp_Relay_2_Ctrl (HB5A) is commanded "High side activated"; AND
any of the signal specified in [1336] is read LOW
within DTI = 200ms.

## R3389
- _Procedure: No activation command to activate dipped beam on driver request. Either of the signals below is read LOW :
  Headlamp_PWR_Status_RH (DI2)
  Headlamp_PWR_Status_LH (DI1)

## R3390
- _Pass criteria: Verify that the warning sent to driver.

## R3391
- _Regression: No

## R3392
- _Time [hr]: 0.1

## R3393
- _Test environment: HIL (manual)

## STC-BDY02-1518

## R3395
- _Object type: Misuse Test

## R3396
- _Status: REVIEWED

## R3397: Status of head lamp activation command detected

## R3398
Upon detection of [STC-BDY02-1384], the ExteriorLightingSafetyZa1 transition to Safe State #BDY02_FL_2.

## R3399
- _Procedure: Status of head lamp activation command detected LOW :
  Either of the signals below is read LOW :
  Headlamp_PWR_Status_RH (DI2)
  Headlamp_PWR_Status_LH (DI1)

## R3400
- _Pass criteria: Verify that the warning sent to driver.

## R3401
- _Regression: No

## R3402
- _Time [hr]: 0.1

## R3403
- _Test environment: HIL (manual)

## STC-BDY02-1519

## R3405
- _Object type: Misuse Test

## R3406
- _Status: REVIEWED

## R3407: Dipped Beam activation

## R3408
The ExteriorLightingSafetyZa1 detect a communication error in the signal [1334] within DTI = 200ms.

## R3409
- _Procedure: Communication error.

## R3410
- _Pass criteria: Verify that the Dipped Beam is activated.
  within DTI = 200ms.

## R3411
- _Regression: No

## R3412
- _Time [hr]: 0.1

## R3413
- _Test environment: HIL (manual)

## STC-BDY02-1520

## R3415
- _Object type: Misuse Test

## R3416
- _Status: REVIEWED

## R3417: Safe State #BDY02_FL_1

## R3418
Upon detection of [STC-BDY02-1519], the ExteriorLightingSafetyZa1 transition to Safe State #BDY02_FL_1.

## R3419
- _Procedure: Communication error.

## R3420
- _Pass criteria: Verify that the Dipped Beam is activated.

## R3421
- _Regression: No

## R3422
- _Time [hr]: 0.1

## R3423
- _Test environment: HIL (manual)

## STC-BDY02-1521

## R3425
- _Object type: Misuse Test

## R3426
- _Status: REVIEWED

## R3427: Communication error on many signals

## R3428
The ExteriorLightingSafetyZa1 detect a communication error in the signal NignitionStatus AND NMasterLightSwitchStatusFuSa=0X4 OR BMasterLightSwitchFaultStatusFuSa = Active, within DTI = 200ms.

## R3429
- _Procedure: Communication error on NignitionStatus.

## R3430
- _Pass criteria: Verify that the Dipped Beam is activated.
  within DTI = 200ms.

## R3431
- _Regression: No

## R3432
- _Time [hr]: 0.1

## R3433
- _Test environment: HIL (manual)

## STC-BDY02-1522

## R3435
- _Object type: Misuse Test

## R3436
- _Status: REVIEWED

## R3437: Safe State #BDY02_FL_1

## R3438
Upon detection of [STC-BDY02-1521], the ExteriorLightingSafetyZa1 transition to Safe State #BDY02_FL_1.

## R3439
- _Procedure: Communication error on NignitionStatus.

## R3440
- _Pass criteria: Verify that the Dipped Beam is activated.

## R3441
- _Regression: No

## R3442
- _Time [hr]: 0.1

## R3443
- _Test environment: HIL (manual)

## STC-BDY02-1523

## R3445
- _Object type: Misuse Test

## R3446
- _Status: REVIEWED

## R3447: E2E protection 1

## R3448
Signals Check

## R3449
- _Procedure: The ExteriorLightingSafetyZa1 command the following signals:
  Headlamp_Relay_2_Ctrl (HB5A)
  Headlamp_Ctrl_PWR_RH (HSD11_2)
  Headlamp_Ctrl_PWR_LH (HSD11_1)
  FlcSafetyStatusMask

## R3450
- _Pass criteria: Verify that the message containing the signal specified is protected with an E2E protection mechanism.

## R3451
- _Regression: No

## R3452
- _Time [hr]: 0.1

## R3453
- _Test environment: HIL (manual)

## STC-BDY02-1525

## R3455
- _Object type: Misuse Test

## R3456
- _Status: REVIEWED

## R3457: E2E protection 2

## R3458
Signal Check

## R3459
- _Procedure: The ExteriorLightingSafetyZa1 output a 32-bits signal called FlcSafetyStatusMask to communicate to the Elc (QM SWC) and ExteriorLightingSafetyZb1 the faults status.

## R3460
- _Pass criteria: Verify that the message containing the signal specified is protected with an E2E protection mechanism.

## R3461
- _Regression: No

## R3462
- _Time [hr]: 0.1

## R3463
- _Test environment: HIL (manual)

## STC-BDY02-1524

## R3465
- _Object type: Misuse Test

## R3466
- _Status: REVIEWED

## R3467: HW failures on Headlamp_Relay_2_Ctrl

## R3468
The ExteriorLightingSafetyZa1 detect HW failures (i.e. short to ground, open, short to battery, out of range) on the signal Headlamp_Relay_2_Ctrl (HB5A) within DTI = 200ms.

## R3469
- _Procedure: HW fault on :
  Headlamp_Relay_2_Ctrl (HB5A)

## R3470
- _Pass criteria: Verify that the warning sent to driver
  ZB1 activate the front light only in case of open circuit.

## R3471
- _Regression: No

## R3472
- _Time [hr]: 0.1

## R3473
- _Test environment: HIL (manual)

## STC-BDY02-1526

## R3475
- _Object type: Misuse Test

## R3476
- _Status: REVIEWED

## R3477: Safe State #BDY02_FL_3

## R3478
Upon detection of [STC-BDY02-1524], the ExteriorLightingSafetyZa1 transition to Safe State #BDY02_FL_3.

## R3479
- _Procedure: HW fault on :
  Headlamp_Relay_2_Ctrl (HB5A)

## R3480
- _Pass criteria: Verify that the warning sent to driver
  ZB1 activate the front light only in case of open circuit.

## R3481
- _Regression: No

## R3482
- _Time [hr]: 0.1

## R3483
- _Test environment: HIL (manual)

## STC-BDY02-1527

## R3485
- _Object type: Misuse Test

## R3486
- _Status: REVIEWED

## R3487: HW failures on Headlamp_Ctrl_PWR_RH and Headlamp_Ctrl_PWR_LH

## R3488
The ExteriorLightingSafetyZa1 detect HW failures (i.e. short to ground, open, short to battery, out of range) on the signals Headlamp_Ctrl_PWR_RH (HSD11_2) and
Headlamp_Ctrl_PWR_LH (HSD11_1) within DTI = 200ms.

## R3489
- _Procedure: HW fault on :
  Headlamp_Ctrl_PWR_RH (HSD11_2
  Headlamp_Ctrl_PWR_LH (HSD11_1)

## R3490
- _Pass criteria: Verify that the warning sent to driver.

## R3491
- _Regression: No

## R3492
- _Time [hr]: 0.1

## R3493
- _Test environment: HIL (manual)

## STC-BDY02-1528

## R3495
- _Object type: Misuse Test

## R3496
- _Status: REVIEWED

## R3497: Safe State #BDY02_FL_2

## R3498
Upon detection of [STC-BDY02-1527], the ExteriorLightingSafetyZa1 shall transition to Safe State #BDY02_FL_2.

## R3499
- _Procedure: HW fault on :
  Headlamp_Ctrl_PWR_RH (HSD11_2
  Headlamp_Ctrl_PWR_LH (HSD11_1)

## R3500
- _Pass criteria: Verify that the warning sent to driver.

## R3501
- _Regression: No

## R3502
- _Time [hr]: 0.1

## R3503
- _Test environment: HIL (manual)

## STC-BDY02-1387

## R3505
- _Object type: Misuse Test

## R3506
- _Status: REVIEWED

## R3507: SW Composition ExteriorLightingSafetyZb2

## R3508
Composition Check

## R3509
- _Procedure: The SW composition ExteriorLightingSafetyZb2 implementing the safety monitoring of this function is designed.

## R3510
- _Pass criteria: Verify that the SW composition is connected to the actuations of the outputs.

## R3511
- _Regression: No

## R3512
- _Time [hr]: 0.1

## R3513
- _Test environment: HIL (manual)

## STC-BDY02-1390

## R3515
- _Object type: Misuse Test

## R3516
- _Status: REVIEWED

## R3517: FlcSafetyStatusMask in fault

## R3518
Command Check

## R3519
- _Procedure: When the signal FlcSafetyStatusMask == "open circuit fault"

## R3520
- _Pass criteria: The ExteriorLightingSafetyZb1 command:
  Headlamp_Relay_2_Ctrl2 (HSD9_1) = "High side activated"
  EflcSafetyStatusMask = bit 1

## R3521
- _Regression: No

## R3522
- _Time [hr]: 0.1

## R3523
- _Test environment: HIL (manual)

## STC-BDY02-1530

## R3525
- _Object type: Misuse Test

## R3526
- _Status: REVIEWED

## R3527: NMasterLightSwitchStatusFuSa value

## R3528
Master Light Switch Resistor Ladder 1 Voltage

## R3529
- _Procedure: The ExteriorLightingSafetyZb1 set the signal NMasterLightSwitchStatusFuSa values accordingly with the voltage of the input signal Master Light Switch Resistor Ladder 1 (AN14_PI2).

## R3530
- _Pass criteria: Verify that the voltage is as for table [1394] and check NMasterLightSwitchStatus.

## R3531
- _Regression: No

## R3532
- _Time [hr]: 0.1

## R3533
- _Test environment: HIL (manual)

## STC-BDY02-1573

## R3535
- _Object type: Misuse Test

## R3536
- _Status: REVIEWED

## R3537: Critical temperature threshold

## R3538
No action is to be taken when DcuMonTemperatureSafetyMaskZb1 = Critical temperature threshold.

## R3539
- _Procedure: DcuMonTemperatureSafetyMaskZb1 = Critical temperature threshold

## R3540
- _Pass criteria: No reaction

## R3541
- _Regression: No

## R3542
- _Time [hr]: 0.1

## R3543
- _Test environment: HIL (manual)

## STC-BDY02-1531

## R3545
- _Object type: Misuse Test

## R3546
- _Status: REVIEWED

## R3547: Input Interfaces

## R3548
Signal Check

## R3549
- _Procedure: The ExteriorLightingSafetyZb1 receive the following signals from the ExteriorLightingSafetyZa1:
  FlcSafetyStatusMask

## R3550
- _Pass criteria: Make Sure ExteriorLightingSafetyZb1 is receiving following signals
  FlcSafetyStatusMask
  Verify that the message containing the signal is protected with appropriate E2E mechanism.

## R3551
- _Regression: No

## R3552
- _Time [hr]: 0.1

## R3553
- _Test environment: Lab-Car (manual)

## STC-BDY02-1533

## R3555
- _Object type: Misuse Test

## R3556
- _Status: REVIEWED

## R3557: Input Interfaces

## R3558
Signals Check

## R3559
- _Procedure: The ExteriorLightingSafetyZb1 receive the following signals:
  Master Light Switch Resistor Ladder 1 (AN14_PI2)
  DcuMonTemperatureSafetyMaskZb1
  NIgnitionStatus

## R3560
- _Pass criteria: Make Sure ExteriorLightingSafetyZb1 is receiving following signals
  Master Light Switch Resistor Ladder 1 (AN14_PI2)
  DcuMonTemperatureSafetyMaskZb1
  NIgnitionStatus

## R3561
- _Regression: No

## R3562
- _Time [hr]: 0.1

## R3563
- _Test environment: Lab-Car (manual)

## STC-BDY02-1393

## R3565
- _Object type: Misuse Test

## R3566
- _Status: REVIEWED

## R3567: HW failures BMasterLightSwitchFaultStatusFuSa (OC)

## R3568
The ExteriorLightingSafetyZb1 detect HW failures (i.e. short to ground, open, short to battery, out of range) on the signal BMasterLightSwitchFaultStatusFuSa within DTI = 200ms.

## R3569
- _Procedure: HW failures (i.e. short to ground, open, short to battery, out of range) on Master LIght Switch

## R3570
- _Pass criteria: Verify that BMasterLightSwitchFaultStatusFuSa = active

## R3571
- _Regression: No

## R3572
- _Time [hr]: 0.1

## R3573
- _Test environment: HIL (manual)

## STC-BDY02-1534

## R3575
- _Object type: Misuse Test

## R3576
- _Status: REVIEWED

## R3577: HW failures BMasterLightSwitchFaultStatusFuSa (OOR)

## R3578
The ExteriorLightingSafetyZb1 detect when the singal BMasterLightSwitchFaultStatusFuSa falls out of the valid ranges as defined in [1394] DTI = 200ms.

## R3579
- _Procedure: Out of range

## R3580
- _Pass criteria: Verify that BMasterLightSwitchFaultStatusFuSa = active

## R3581
- _Regression: No

## R3582
- _Time [hr]: 0.1

## R3583
- _Test environment: HIL (manual)

## STC-BDY02-1535

## R3585
- _Object type: Misuse Test

## R3586
- _Status: REVIEWED

## R3587: BMasterLightSwitchFaultStatusFuSa Status

## R3588
Upon detection of [1339] or [1726], the ExteriorLightingSafetyZb1 set BMasterLightSwitchFaultStatusFuSa to Active wihtin FRT = 100ms.

## R3589
- _Procedure: HW failures (i.e. short to ground, open, short to battery, out of range) or out of range

## R3590
- _Pass criteria: Verify that BMasterLightSwitchFaultStatusFuSa = active within FRT =100ms and EflcSafetyStatusMask = bit2 to 3

## R3591
- _Regression: No

## R3592
- _Time [hr]: 0.1

## R3593
- _Test environment: HIL (manual)

## STC-BDY02-1532

## R3595
- _Object type: Misuse Test

## R3596
- _Status: REVIEWED

## R3597: Command Signal

## R3598
Signal Check

## R3599
- _Procedure: The ExteriorLightingSafetyZb1 command the following signals:
  Headlamp_Relay_2_Ctrl2 (HSD9_1)

## R3600
- _Pass criteria: Verify that the ExteriorLightingSafetyZb1 command the signal.

## R3601
- _Regression: No

## R3602
- _Time [hr]: 0.1

## R3603
- _Test environment: HIL (manual)

## STC-BDY02-1536

## R3605
- _Object type: Misuse Test

## R3606
- _Status: REVIEWED

## R3607: E2E Protection 1

## R3608
Signals Check

## R3609
- _Procedure: The ExteriorLightingSafetyZb1 command the following signals to the ExteriorLightingSafetyZa1 and ExteriorLightingSafetyZc1:
  EflcSafetyStatusMask
  NMasterLightSwitchStatusFuSa
  BMasterLightSwitchFaultStatusFuSa

## R3610
- _Pass criteria: Verify that the ExteriorLightingSafetyZb1 command the signals and that the message containing the signal specified EflcSafetyStatusMask is protected with an E2E protection mechanism.

## R3611
- _Regression: No

## R3612
- _Time [hr]: 0.1

## R3613
- _Test environment: HIL (manual)

## STC-BDY02-1396

## R3615
- _Object type: Misuse Test

## R3616
- _Status: REVIEWED

## R3617: HW Fault on Headlamp_Relay_2_Ctrl

## R3618
The ExteriorLightingSafetyZb1 detect HW failures (i.e. short to ground, open, short to battery, out of range) on the signal Headlamp_Relay_2_Ctrl within DTI = 200ms.

## R3619
- _Procedure: HW Fault on Headlamp_Relay_2_Ctrl (HB5A)

## R3620
- _Pass criteria: Verify that EflcSafetyStatusMask = bit 4 to 7

## R3621
- _Regression: No

## R3622
- _Time [hr]: 0.1

## R3623
- _Test environment: HIL (manual)

## STC-BDY02-1538

## R3625
- _Object type: Misuse Test

## R3626
- _Status: REVIEWED

## R3627: HW Fault on Headlamp_Relay_2_Ctrl

## R3628
Upon detection of [STC-BDY02-1396], the ExteriorLightingSafetyZb1 set EflcSafetyStatusMask = bit 4 to 7 wihtin FRT = 100ms

## R3629
- _Procedure: HW Fault on Headlamp_Relay_2_Ctrl (HB5A)

## R3630
- _Pass criteria: Verify that EflcSafetyStatusMask = bit 4 to 7

## R3631
- _Regression: No

## R3632
- _Time [hr]: 0.1

## R3633
- _Test environment: HIL (manual)

## STC-BDY02-1399

## R3635
- _Object type: Misuse Test

## R3636
- _Status: REVIEWED

## R3637: SW Composition ExteriorLightingSafetyZc1

## R3638
Composition Check

## R3639
- _Procedure: The SW composition ExteriorLightingSafetyZc1 implementing the safety monitoring of this function is designed.

## R3640
- _Pass criteria: Verify that the SW composition is the only connected to the actuations of the outputs.

## R3641
- _Regression: No

## R3642
- _Time [hr]: 0.1

## R3643
- _Test environment: HIL (manual)

## STC-BDY02-1539

## R3645
- _Object type: Misuse Test

## R3646
- _Status: REVIEWED

## R3647: SW Composition Brake/Tail Light Contro

## R3648
Composition Check

## R3649
- _Procedure: The SW composition Brake/Tail Light Control is defined.

## R3650
- _Pass criteria: Verify that the compositions Master Light Control is not connected to any actuation of the outputs.

## R3651
- _Regression: No

## R3652
- _Time [hr]: 0.1

## R3653
- _Test environment: HIL (manual)

## STC-BDY02-1402

## R3655
- _Object type: Misuse Test

## R3656
- _Status: REVIEWED

## R3657: Stop Tail Command

## R3658
Command Check

## R3659
- _Procedure: The ExteriorLightingSafetyZc1 command
  Stop_Tail_Outboard_PWR_RH (HSD3)
  Stop_Tail_Inboard_PWR_RH (HSD4)
  Stop_Tail_Outboard_PWR_LH (HSD8)
  Stop_Tail_Inboard_PWR_LH (HSD7)
  as requested by
  NLHTailInboardLampActivate_Req
  NLHTailOutboardLampActivate_Req
  NRHTailInboardLampActivate_Req
  NRHTailOutboardLampActivate_Req

## R3660
- _Pass criteria: Verify that the command is at all times.

## R3661
- _Regression: No

## R3662
- _Time [hr]: 0.1

## R3663
- _Test environment: HIL (manual)

## STC-BDY02-1540

## R3665
- _Object type: Misuse Test

## R3666
- _Status: REVIEWED

## R3667: BrakeLightConditionHappen Status 1

## R3668
The ExteriorLightingSafetyZc1 set BrakeLightConditionHappen to true when either of the following occurs:
Brake Pedal is pressed (NBrakepedalStatus_Q == Valid && NBrakepedalStatus == Pressed)
Deceleration is above LongActiveThreshold calibratable ( gLongitudinal < -1.3 m/s2 only && gLongitudinal_Q = Valid)

## R3669
- _Procedure: Test Steps :
  NBrakepedalStatus_Q == Valid && NBrakepedalStatus == Pressed
  NgLongitudinal_Q == Valid && gLongitudinal < -1.3 m/s2

## R3670
- _Pass criteria: Verify that BrakeLightConditionHappen =True.

## R3671
- _Regression: No

## R3672
- _Time [hr]: 0.1

## R3673
- _Test environment: HIL (manual)

## STC-BDY02-1541

## R3675
- _Object type: Misuse Test

## R3676
- _Status: REVIEWED

## R3677: BrakeLightConditionHappen Status 2

## R3678
The ExteriorLightingSafetyZc1 shall set BrakeLightConditionHappen to true when all the following occurs:
NBrakepedalStatus_Q != Valid
NpBrake_Q == Valid
pBrake > pBrakeThresholdActive

## R3679
- _Procedure: NBrakepedalStatus_Q != Valid && NpBrake_Q == Valid && pBrake >= pBrakeThresholdActive

## R3680
- _Pass criteria: Verify that BrakeLightConditionHappen =True.

## R3681
- _Regression: No

## R3682
- _Time [hr]: 0.1

## R3683
- _Test environment: HIL (manual)

## STC-BDY02-1542

## R3685
- _Object type: Misuse Test

## R3686
- _Status: REVIEWED

## R3687: Stop Tail Duty Cycle

## R3688
Lamp Intensity Check

## R3689
- _Procedure: The ExteriorLightingSafetyZc1 set the duty cycle of the outputs :
  Stop_Tail_Outboard_PWR_RH (HSD3)
  Stop_Tail_Inboard_PWR_RH (HSD4)
  Stop_Tail_Outboard_PWR_LH (HSD8)
  Stop_Tail_Inboard_PWR_LH (HSD7)
  as requested by
  NTailInboardLampIntensity_Req
  NTailOutboardLampIntensity_Req

## R3690
- _Pass criteria: Verify that the command is at all times.

## R3691
- _Regression: No

## R3692
- _Time [hr]: 0.1

## R3693
- _Test environment: HIL (manual)

## STC-BDY02-1404

## R3695
- _Object type: Misuse Test

## R3696
- _Status: REVIEWED

## R3697: Command Brake Light 1

## R3698
The ExteriorLightingSafetyZc1 detect when:
BrakeLightConditionHappen is set to true;
AND
NLHTailInboardLampActivate_Req = 'no request' AND
NLHTailOutboardLampActivate_Req = 'no request' AND
NRHTailInboardLampActivate_Req = 'no request' AND
NRHTailOutboardLampActivate_Req = 'no request'; AND
NIgnitionStatus ==0x5 (Ignition)
within DTI = 100ms.

## R3699
- _Procedure: Test Steps :
  BrakeLightConditionHappen is set to true
  NLHTailInboardLampActivate_Req = 'no request'
  NLHTailOutboardLampActivate_Req = 'no request'
  NRHTailInboardLampActivate_Req = 'no request'
  NRHTailOutboardLampActivate_Req = 'no request'
  NIgnitionStatus ==0x5 (Ignition)
  within DTI = 100ms.

## R3700
- _Pass criteria: Verify that the Command brake light :
  Stop_Tail_Outboard_PWR_RH (HSD3)
  Stop_Tail_Inboard_PWR_RH (HSD4)
  Stop_Tail_Outboard_PWR_LH (HSD8)
  Stop_Tail_Inboard_PWR_LH (HSD7)

## R3701
- _Regression: No

## R3702
- _Time [hr]: 0.1

## R3703
- _Test environment: HIL (manual)

## STC-BDY02-1543

## R3705
- _Object type: Misuse Test

## R3706
- _Status: REVIEWED

## R3707: Safe State #BDY02_RL_1

## R3708
Upon detection of [STC-BDY02-1404] the ExteriorLightingSafetyZc1 transition to Safe State #BDY02_RL_1.

## R3709
- _Procedure: Test Steps :
  BrakeLightConditionHappen is set to true
  NLHTailInboardLampActivate_Req = 'no request'
  NLHTailOutboardLampActivate_Req = 'no request'
  NRHTailInboardLampActivate_Req = 'no request'
  NRHTailOutboardLampActivate_Req = 'no request'
  NIgnitionStatus ==0x5 (Ignition)
  within DTI = 100ms.

## R3710
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)

## R3711
- _Regression: No

## R3712
- _Time [hr]: 0.1

## R3713
- _Test environment: HIL (manual)

## STC-BDY02-1544

## R3715
- _Object type: Misuse Test

## R3716
- _Status: REVIEWED

## R3717: Command Brake Light 2

## R3718
The ExteriorLightingSafetyZc1 detect when:
NMasterLightSwitchStatusFuSa != 0x0 (OFF)
AND
BrakeLightConditionHappen is set false AND
NLHTailInboardLampActivate_Req = 'no request' AND
NLHTailOutboardLampActivate_Req = 'no request' AND
NRHTailInboardLampActivate_Req = 'no request' AND
NRHTailOutboardLampActivate_Req = 'no request'; AND
NIgnitionStatus ==0x5 (Ignition)
within DTI = 100ms.

## R3719
- _Procedure: Test Steps :
  NMasterLightSwitchStatusFuSa != 0x0 (OFF)
  BrakeLightCondition is set false
  NLHTailInboardLampActivate_Req = 'no request'
  NLHTailOutboardLampActivate_Req = 'no request'
  NRHTailInboardLampActivate_Req = 'no request'
  NRHTailOutboardLampActivate_Req = 'no request'
  NIgnitionStatus ==0x5 (Ignition)

## R3720
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)
  within 100ms

## R3721
- _Regression: No

## R3722
- _Time [hr]: 0.1

## R3723
- _Test environment: HIL (manual)

## STC-BDY02-1545

## R3725
- _Object type: Misuse Test

## R3726
- _Status: REVIEWED

## R3727: Command Brake Light 3

## R3728
The ExteriorLightingSafetyZc1 detect when:
BMasterLightSwitchFaultStatusFuSa = 0x1 (TRUE STATE meaning ACTIVE FAULT)
AND
BrakeLightConditionHappen is set false AND
NLHTailInboardLampActivate_Req = 'no request' AND
NLHTailOutboardLampActivate_Req = 'no request' AND
NRHTailInboardLampActivate_Req = 'no request' AND
NRHTailOutboardLampActivate_Req = 'no request';AND
NIgnitionStatus ==0x5 (Ignition)
within DTI = 100ms.

## R3729
- _Procedure: Test Steps :
  BMasterLightSwitchFaultStatusFuSa = Active
  BrakeLightCondition is set false
  NLHTailInboardLampActivate_Req = 'no request'
  NLHTailOutboardLampActivate_Req = 'no request'
  NRHTailInboardLampActivate_Req = 'no request'
  NRHTailOutboardLampActivate_Req = 'no request'
  NIgnitionStatus ==0x5 (Ignition)

## R3730
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)
  within 100ms

## R3731
- _Regression: No

## R3732
- _Time [hr]: 0.1

## R3733
- _Test environment: HIL (manual)

## STC-BDY02-1546

## R3735
- _Object type: Misuse Test

## R3736
- _Status: REVIEWED

## R3737: Safe State #BDY02_RL_2

## R3738
Upon detection of [STC-BDY02-1544] or [STC-BDY02-1545] the ExteriorLightingSafetyZc1 transition to Safe State #BDY02_RL_2.

## R3739
- _Procedure: Test Steps :
  BMasterLightSwitchFaultStatusFuSa = Active
  BrakeLightCondition is set false
  NLHTailInboardLampActivate_Req = 'no request'
  NLHTailOutboardLampActivate_Req = 'no request'
  NRHTailInboardLampActivate_Req = 'no request'
  NRHTailOutboardLampActivate_Req = 'no request'
  NIgnitionStatus ==0x5 (Ignition)

## R3740
- _Pass criteria: Verify that the Command brake light :
  Stop_Tail_Outboard_PWR_RH (HSD3)
  Stop_Tail_Inboard_PWR_RH (HSD4)
  Stop_Tail_Outboard_PWR_LH (HSD8
  Stop_Tail_Inboard_PWR_LH (HSD7)

## R3741
- _Regression: No

## R3742
- _Time [hr]: 0.1

## R3743
- _Test environment: HIL (manual)

## STC-BDY02-1547

## R3745
- _Object type: Misuse Test

## R3746
- _Status: REVIEWED

## R3747: Command Brake Light 4 (88%)

## R3748
The ExteriorLightingSafetyZc1 detect when:
BMasterLightSwitchFaultStatusFuSa = 0x1 (TRUE STATE meaning ACTIVE FAULT) OR NMasterLightSwitchStatusFuSa != 0x0 (OFF) AND
(NTailInboardLampIntensity_Req <65% OR NTailInboardLampIntensity_Req <65%) AND
NIgnitionStatus ==0x5 (Ignition)
within DTI = 100ms.

## R3749
- _Procedure: Rear Light request active

## R3750
- _Pass criteria: Verify that the Command 88% :
  Stop_Tail_Outboard_PWR_RH (HSD3)
  Stop_Tail_Inboard_PWR_RH (HSD4)
  Stop_Tail_Outboard_PWR_LH (HSD8
  Stop_Tail_Inboard_PWR_LH (HSD7)
  within 100ms

## R3751
- _Regression: No

## R3752
- _Time [hr]: 0.1

## R3753
- _Test environment: HIL (manual)

## STC-BDY02-1548

## R3755
- _Object type: Misuse Test

## R3756
- _Status: REVIEWED

## R3757: Safe State #BDY02_RL_2

## R3758
Upon detection of [STC-BDY02-1544] or [STC-BDY02-1545] the ExteriorLightingSafetyZc1 transition to Safe State #BDY02_RL_2.

## R3759
- _Procedure: Rear Light request active

## R3760
- _Pass criteria: Verify that the Command 88% :
  Stop_Tail_Outboard_PWR_RH (HSD3)
  Stop_Tail_Inboard_PWR_RH (HSD4)
  Stop_Tail_Outboard_PWR_LH (HSD8
  Stop_Tail_Inboard_PWR_LH (HSD7)

## R3761
- _Regression: No

## R3762
- _Time [hr]: 0.1

## R3763
- _Test environment: HIL (manual)

## STC-BDY02-1549

## R3765
- _Object type: Misuse Test

## R3766
- _Status: REVIEWED

## R3767: Command Brake Light 5 (100%)

## R3768
The ExteriorLightingSafetyZc1 detect when:
BrakeLightConditionHappen is set TRUE AND
(NTailInboardLampIntensity_Req <65% OR NTailOutboardLampIntensity_Req <65%)
within DTI = 100ms.

## R3769
- _Procedure: Brake Light condition is true

## R3770
- _Pass criteria: Verify that the Command 100% :
  Stop_Tail_Outboard_PWR_RH (HSD3)
  Stop_Tail_Inboard_PWR_RH (HSD4)
  Stop_Tail_Outboard_PWR_LH (HSD8
  Stop_Tail_Inboard_PWR_LH (HSD7)
  within 100ms

## R3771
- _Regression: No

## R3772
- _Time [hr]: 0.1

## R3773
- _Test environment: HIL (manual)

## STC-BDY02-1550

## R3775
- _Object type: Misuse Test

## R3776
- _Status: REVIEWED

## R3777: Safe State #BDY02_RL_1

## R3778
Upon detection of [STC-BDY02-1544] or [STC-BDY02-1545] the ExteriorLightingSafetyZc1 transition to Safe State #BDY02_RL_1.

## R3779
- _Procedure: Brake Light condition is true

## R3780
- _Pass criteria: Verify that the Command 100% :
  Stop_Tail_Outboard_PWR_RH (HSD3)
  Stop_Tail_Inboard_PWR_RH (HSD4)
  Stop_Tail_Outboard_PWR_LH (HSD8
  Stop_Tail_Inboard_PWR_LH (HSD7)

## R3781
- _Regression: No

## R3782
- _Time [hr]: 0.1

## R3783
- _Test environment: HIL (manual)

## STC-BDY02-1551

## R3785
- _Object type: Misuse Test

## R3786
- _Status: REVIEWED

## R3787: No reaction with critical temperature

## R3788
No action is to be taken when DcuMonTemperatureSafetyMaskZc1 = Critical temperature threshold.

## R3789
- _Procedure: DcuMonTemperatureSafetyMaskZC1 = Critical temperature

## R3790
- _Pass criteria: No reaction

## R3791
- _Regression: No

## R3792
- _Time [hr]: 0.1

## R3793
- _Test environment: HIL (manual)

## STC-BDY02-1407

## R3795
- _Object type: Misuse Test

## R3796
- _Status: REVIEWED

## R3797: High Side Command Stop Tail Light with with 100% duty

## R3798
Stop Tail Light command

## R3799
- _Procedure: The ExteriorLightingSafetyZc1 command 100% the outputs:
  Stop_Tail_Outboard_PWR_RH (HSD3)
  Stop_Tail_Inboard_PWR_RH (HSD4)
  Stop_Tail_Outboard_PWR_LH (HSD8)
  Stop_Tail_Inboard_PWR_LH (HSD7)

## R3800
- _Pass criteria: Verify that Stop Tail Light are commanded.

## R3801
- _Regression: No

## R3802
- _Time [hr]: 0.1

## R3803
- _Test environment: HIL (manual)

## STC-BDY02-1552

## R3805
- _Object type: Misuse Test

## R3806
- _Status: REVIEWED

## R3807: High Side Command Stop Tail Light with with 88% duty

## R3808
- _Procedure: The ExteriorLightingSafetyZc1 command 88% the outputs:
  Stop_Tail_Outboard_PWR_RH (HSD3)
  Stop_Tail_Inboard_PWR_RH (HSD4)
  Stop_Tail_Outboard_PWR_LH (HSD8)
  Stop_Tail_Inboard_PWR_LH (HSD7)

## R3809
- _Pass criteria: Verify that Stop Tail Light are commanded.

## R3810
- _Regression: No

## R3811
- _Time [hr]: 0.1

## R3812
- _Test environment: HIL (manual)

## STC-BDY02-1553

## R3814
- _Object type: Misuse Test

## R3815
- _Status: REVIEWED

## R3816: NRlcSafetyClusterMessage Fault

## R3817
Signal Check

## R3818
- _Procedure: The ExteriorLightingSafetyZc1 command the below signal:
  NRlcSafetyClusterMessage = "fault value"

## R3819
- _Pass criteria: Verify that the signal is in fault.

## R3820
- _Regression: No

## R3821
- _Time [hr]: 0.1

## R3822
- _Test environment: HIL (manual)

## STC-BDY02-1410

## R3824
- _Object type: Misuse Test

## R3825
- _Status: REVIEWED

## R3826: Brake Light request

## R3827
While in Safe State #BDY02_RL_1, the ExteriorLightingSafetyZc1 perform the action specified in [1648] within FRT = 100 ms.

## R3828
- _Procedure: Test Steps :
  BrakeLightConditionHappen is set to true;
  &&
  NRHTailLampActivate_Req =no request; &&
  NLHTailLampActivate_Req = norequest;
  OR
  Communication Error on any of the below signals :
  - NBrakePedalSwitch1Status
  NBrakePedalSwitch2Status
  pBrake
  gLongitudinal
  NgLongitudinal_Q

## R3829
- _Pass criteria: Verify the Brake Light requested.
  within 100ms

## R3830
- _Regression: No

## R3831
- _Time [hr]: 0.1

## R3832
- _Test environment: HIL (manual)

## STC-BDY02-1554

## R3834
- _Object type: Misuse Test

## R3835
- _Status: REVIEWED

## R3836: Exit Safe State #BDY02_1

## R3837
The ExteriorLightingSafetyZc1 exit Safe State #BDY02_RL_1 at the new vehicle ignition cycle or after a healing time interval, HTI= 3 secs, when the fault no longer exists.

## R3838
- _Procedure: Next ignition cycle

## R3839
- _Pass criteria: Verify the Exit Safe State #BDY02_1 and Normal Operation of ElcSafety.

## R3840
- _Regression: No

## R3841
- _Time [hr]: 0.1

## R3842
- _Test environment: HIL (manual)

## STC-BDY02-1555

## R3844
- _Object type: Misuse Test

## R3845
- _Status: REVIEWED

## R3846: Tail light activation

## R3847
While in Safe State #BDY02_RL_2, the ExteriorLightingSafetyZc1 perform the action specified in [1649] within FRT = 100 ms.

## R3848
- _Procedure: Test Steps :
  Master Light switch status = Step4 && BLH_DipperBeamActivate_Req = No activation request & BRH_DippedBeamActivate_Req = No activation request
  HW failures (i.e. short to ground, open, short to battery, out of range) on the signal specified in [1334]

## R3849
- _Pass criteria: Verify the tail light activated
  within 100ms

## R3850
- _Regression: No

## R3851
- _Time [hr]: 0.1

## R3852
- _Test environment: HIL (manual)

## STC-BDY02-1413

## R3854
- _Object type: Misuse Test

## R3855
- _Status: REVIEWED

## R3856: Exit Safe State #BDY02_2

## R3857
The ExteriorLightingSafetyZc1 exit Safe State #BDY02_RL_2 at the new vehicle ignition cycle or after a healing time interval, HTI= 3 secs, when the fault no longer exists.

## R3858
- _Procedure: Next Ignition Cycle

## R3859
- _Pass criteria: Verify the Exit Safe State #BDY02_2 and Normal Operation of ElcSafety

## R3860
- _Regression: No

## R3861
- _Time [hr]: 0.1

## R3862
- _Test environment: HIL (manual)

## STC-BDY02-1556

## R3864
- _Object type: Misuse Test

## R3865
- _Status: REVIEWED

## R3866: Brake Light/Tail Ligt warning

## R3867
While in Safe State #BDY02_RL_3, the ExteriorLightingSafetyZc1 perform the action specified in [1653] within FRT = 100 ms.

## R3868
- _Procedure: HW Fault in :
  Stop_Tail_Outboard_PWR_RH (HSD3)
  Stop_Tail_Inboard_PWR_RH (HSD4)
  Stop_Tail_Outboard_PWR_LH (HSD8)
  Stop_Tail_Inboard_PWR_LH (HSD7)

## R3869
- _Pass criteria: Verify the Warning sent to driver (Brake Light/Tail Ligt warning)
  within 100ms

## R3870
- _Regression: No

## R3871
- _Time [hr]: 0.1

## R3872
- _Test environment: HIL (manual)

## STC-BDY02-1416

## R3874
- _Object type: Misuse Test

## R3875
- _Status: REVIEWED

## R3876: Exit Safe State #BDY02_4

## R3877
The ExteriorLightingSafetyZc1 exit Safe State #BDY02_RL_3 at the new vehicle ignition cycle or after a healing time interval, HTI= 3 secs, when the fault no longer exists.

## R3878
- _Procedure: Next Ignition Cycle

## R3879
- _Pass criteria: Exit Safe State #BDY02_4 and Normal Operation of ElcSafety

## R3880
- _Regression: No

## R3881
- _Time [hr]: 0.1

## R3882
- _Test environment: HIL (manual)

## STC-BDY02-1557

## R3884
- _Object type: Misuse Test

## R3885
- _Status: REVIEWED

## R3886: E2E Protection for input signals 1

## R3887
Signals Check

## R3888
- _Procedure: The ExteriorLightingSafetyZc1 receive the following signals:
  NBrakePedalStatus
  NBrakePedalStatus_Q
  pBrake
  pBrake_Q
  gLongitudinal
  NgLongitudinal_Q

## R3889
- _Pass criteria: Verify that the message containing the signals is protected with an E2E protection mechanism.

## R3890
- _Regression: No

## R3891
- _Time [hr]: 0.1

## R3892
- _Test environment: HIL (manual)

## STC-BDY02-1558

## R3894
- _Object type: Misuse Test

## R3895
- _Status: REVIEWED

## R3896: Request Received Signals

## R3897
Signals Check

## R3898
- _Procedure: The ExteriorLightingSafetyZc1 receive the following signals:
  NLHTailInboardLampActivate_Req
  NLHTailOutboardLampActivate_Req
  NRHTailInboardLampActivate_Req
  NRHTailOutboardLampActivate_Req
  NTailInboardLampIntensity_Req
  NTailOutboardLampIntensity_Req
  DcuMonTemperatureSafetyMaskZc1

## R3899
- _Pass criteria: Verify that the request signals are received.

## R3900
- _Regression: No

## R3901
- _Time [hr]: 0.1

## R3902
- _Test environment: HIL (manual)

## STC-BDY02-1559

## R3904
- _Object type: Misuse Test

## R3905
- _Status: REVIEWED

## R3906: E2E Protection for input signals 2

## R3907
Signals Check

## R3908
- _Procedure: The ExteriorLightingSafetyZc1 shall receive the following signals:
  NMasterLightSwitchStatusFuSa
  BMasterLightSwitchFaultStatusFuSa
  EflcSafetyStatusMask
  NIgnitionStatus

## R3909
- _Pass criteria: Verify that the message containing the signals is protected with an E2E protection mechanism.

## R3910
- _Regression: No

## R3911
- _Time [hr]: 0.1

## R3912
- _Test environment: HIL (manual)

## STC-BDY02-1420

## R3914
- _Object type: Misuse Test

## R3915
- _Status: REVIEWED

## R3916: Brake Light Requested (1)

## R3917
The ExteriorLightingSafetyZc1 detect if a communication error occurs in the transmission of the signals specified in [1686], [1688] within DTI = 200ms.

## R3918
- _Procedure: Communication Error on any of the below signals :
  NBrakePedalStatus
  pBrake
  gLongitudinal
  NgLongitudinal_Q

## R3919
- _Pass criteria: Verify the Brake Light Requested
  within 200 ms

## R3920
- _Regression: No

## R3921
- _Time [hr]: 0.1

## R3922
- _Test environment: HIL (manual)

## STC-BDY02-1560

## R3924
- _Object type: Misuse Test

## R3925
- _Status: REVIEWED

## R3926: Safe State #BDY02_RL_1 (1)

## R3927
Upon detection of [1696] the ExteriorLightingSafetyZc1 transition to Safe State #BDY02_RL_1.

## R3928
- _Procedure: Communication Error on any of the below signals :
  NBrakePedalStatus
  pBrake
  gLongitudinal
  NgLongitudinal_Q

## R3929
- _Pass criteria: Verify the Brake Light Requested

## R3930
- _Regression: No

## R3931
- _Time [hr]: 0.1

## R3932
- _Test environment: HIL (manual)

## STC-BDY02-1561

## R3934
- _Object type: Misuse Test

## R3935
- _Status: REVIEWED

## R3936: Tail light activation 1

## R3937
The ExteriorLightingSafetyZc1 detect if a communication error occurs in the transmission of the signals specified in [1691] within DTI = 200ms.

## R3938
- _Procedure: Communication Error on any of the below signals :
  NMasterLightSwitchStatusFuSa
  BMasterLightSwitchFaultStatusFuSa

## R3939
- _Pass criteria: Verify the tail light activation
  within 200ms

## R3940
- _Regression: No

## R3941
- _Time [hr]: 0.1

## R3942
- _Test environment: HIL (manual)

## STC-BDY02-1562

## R3944
- _Object type: Misuse Test

## R3945
- _Status: REVIEWED

## R3946: Safe State #BDY02_RL_2 (1)

## R3947
Upon detection of [1733] the ExteriorLightingSafetyZc1 transition to Safe State #BDY02_RL_2.

## R3948
- _Procedure: Communication Error on any of the below signals :
  NMasterLightSwitchStatusFuSa
  BMasterLightSwitchFaultStatusFuSa

## R3949
- _Pass criteria: Verify the tail light activation

## R3950
- _Regression: No

## R3951
- _Time [hr]: 0.1

## R3952
- _Test environment: HIL (manual)

## STC-BDY02-1563

## R3954
- _Object type: Misuse Test

## R3955
- _Status: REVIEWED

## R3956: Tail light activation 2

## R3957
The ExteriorLightingSafetyZc1 detect if a communication error occurs in the transmission of the signals specified in [1817] AND
(( NMasterLightSwitchStatusFuSa != 0x0 (OFF) OR (BMasterLightSwitchFaultStatusFuSa = 0x1 (TRUE STATE meaning ACTIVE FAULT)) AND BrakeLightConditionHappen is set false) within DTI = 200ms.

## R3958
- _Procedure: Communication Error on any of the below signals :
  NignitionStatus
  No Tail Light Request
  Brakelightcondition is false

## R3959
- _Pass criteria: Verify the tail light activation

## R3960
- _Regression: No

## R3961
- _Time [hr]: 0.1

## R3962
- _Test environment: HIL (manual)

## STC-BDY02-1564

## R3964
- _Object type: Misuse Test

## R3965
- _Status: REVIEWED

## R3966: Safe State #BDY02_RL_2 (2)

## R3967
Upon detection of [STC-BDY02-1563] the ExteriorLightingSafetyZc1 shall transition to Safe State #BDY02_RL_2.

## R3968
- _Procedure: Communication Error on any of the below signals :
  NignitionStatus
  No Tail Light Request
  Brakelightcondition is false

## R3969
- _Pass criteria: Verify the tail light activation

## R3970
- _Regression: No

## R3971
- _Time [hr]: 0.1

## R3972
- _Test environment: HIL (manual)

## STC-BDY02-1565

## R3974
- _Object type: Misuse Test

## R3975
- _Status: REVIEWED

## R3976: Brake Light Requested (2)

## R3977
The ExteriorLightingSafetyZc1 detect if a communication error occurs in the transmission of the signals specified in [1817] AND BrakeLightConditionHappen is set TRUE within DTI = 200ms.

## R3978
- _Procedure: Communication Error on any of the below signals :
  NignitionStatus
  No Tail Light Request
  Brakelightcondition is true

## R3979
- _Pass criteria: Verify the Brake Light Requested
  within 200ms

## R3980
- _Regression: No

## R3981
- _Time [hr]: 0.1

## R3982
- _Test environment: HIL (manual)

## STC-BDY02-1566

## R3984
- _Object type: Misuse Test

## R3985
- _Status: REVIEWED

## R3986: Safe State #BDY02_RL_1 (2)

## R3987
Upon detection of [STC-BDY02-1565] the ExteriorLightingSafetyZc1 transition to Safe State #BDY02_RL_1.

## R3988
- _Procedure: Communication Error on any of the below signals :
  NignitionStatus
  No Tail Light Request
  Brakelightcondition is true

## R3989
- _Pass criteria: Verify the Brake Light Requested

## R3990
- _Regression: No

## R3991
- _Time [hr]: 0.1

## R3992
- _Test environment: HIL (manual)

## STC-BDY02-1567

## R3994
- _Object type: Misuse Test

## R3995
- _Status: REVIEWED

## R3996: Brake Light Requested (3)

## R3997
The ExteriorLightingSafetyZc1 detect within DTI = 200ms if:
(pBrake_Q != valid && NBrakepedalStatus_Q != valid ) || gLongitudinal_Q != valid

## R3998
- _Procedure: Test Step :
  (pBrake_Q != valid && NBrakepedalStatus_Q != valid ) || gLogitudinal_Q != valid

## R3999
- _Pass criteria: Verify the Brake Light Requested

## R4000
- _Regression: No

## R4001
- _Time [hr]: 0.1

## R4002
- _Test environment: HIL (manual)

## STC-BDY02-1568

## R4004
- _Object type: Misuse Test

## R4005
- _Status: REVIEWED

## R4006: Safe State #BDY02_RL_1 (3)

## R4007
Upon detection of [STC-BDY02-1567] the ExteriorLightingSafetyZc1 shall transition to Safe State #BDY02_RL_1.

## R4008
- _Procedure: Test Step :
  (pBrake_Q != valid && NBrakepedalStatus_Q != valid ) || gLogitudinal_Q != valid

## R4009
- _Pass criteria: Verify the Brake Light Requested

## R4010
- _Regression: No

## R4011
- _Time [hr]: 0.1

## R4012
- _Test environment: HIL (manual)

## STC-BDY02-1569

## R4014
- _Object type: Misuse Test

## R4015
- _Status: REVIEWED

## R4016: Command Sent Signals

## R4017
Signals Check

## R4018
- _Procedure: The ExteriorLightingSafetyZc1 command the following signals:
  Stop_Tail_Outboard_PWR_RH (HSD3)
  Stop_Tail_Inboard_PWR_RH (HSD4)
  Stop_Tail_Outboard_PWR_LH (HSD8
  Stop_Tail_Inboard_PWR_LH (HSD7)

## R4019
- _Pass criteria: Verify that the command signals are sent.

## R4020
- _Regression: No

## R4021
- _Time [hr]: 0.1

## R4022
- _Test environment: HIL (manual)

## STC-BDY02-1570

## R4024
- _Object type: Misuse Test

## R4025
- _Status: REVIEWED

## R4026: E2E Protection for output signals

## R4027
Signals Check

## R4028
- _Procedure: The ExteriorLightingSafetyZc1 shall command the following signal to ADI
  NRlcSafetyClusterMessage
  RlcSafetyStatusMask

## R4029
- _Pass criteria: Verify that the message containing the signals is protected with an E2E protection mechanism.

## R4030
- _Regression: No

## R4031
- _Time [hr]: 0.1

## R4032
- _Test environment: HIL (manual)

## STC-BDY02-1571

## R4034
- _Object type: Misuse Test

## R4035
- _Status: REVIEWED

## R4036: Brake Light/Tail Light warning sent to driver

## R4037
The ExteriorLightingSafetyZc1 detect HW failures (i.e. short to ground, open, short to battery, out of range) on the signal specified in [1705] within DTI = 200ms.

## R4038
- _Procedure: HW Fault on :
  Stop_Tail_Outboard_PWR_RH (HSD3)
  Stop_Tail_Inboard_PWR_RH (HSD4)
  Stop_Tail_Outboard_PWR_LH (HSD8)
  Stop_Tail_Inboard_PWR_LH (HSD7)

## R4039
- _Pass criteria: Verify that the Warning sent to driver (Brake Light/Tail Light warning)
  within 200ms

## R4040
- _Regression: No

## R4041
- _Time [hr]: 0.1

## R4042
- _Test environment: HIL (manual)

## STC-BDY02-1572

## R4044
- _Object type: Misuse Test

## R4045
- _Status: REVIEWED

## R4046: Safe State #BDY02_RL_3

## R4047
Upon detection of [STC-BDY02-1571], the ExteriorLightingSafetyZc1 transition to Safe State #BDY02_RL_3.

## R4048
- _Procedure: HW Fault on :
  Stop_Tail_Outboard_PWR_RH (HSD3)
  Stop_Tail_Inboard_PWR_RH (HSD4)
  Stop_Tail_Outboard_PWR_LH (HSD8)
  Stop_Tail_Inboard_PWR_LH (HSD7)

## R4049
- _Pass criteria: Verify that the Warning sent to driver (Brake Light/Tail Light warning)

## R4050
- _Regression: No

## R4051
- _Time [hr]: 0.1

## R4052
- _Test environment: HIL (manual)
